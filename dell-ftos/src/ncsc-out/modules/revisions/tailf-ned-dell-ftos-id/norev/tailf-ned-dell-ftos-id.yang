module tailf-ned-dell-ftos-id {
  // Generated by yanger -t ncs
  tailf:ncs-device-type "cli-ned";

  namespace "http://tail-f.com/ned/dell-ftos-id";
  prefix force10-id;

  import tailf-ncs-ned {
    prefix ned;
  }
  import tailf-ncs {
    prefix ncs;
  }
  import tailf-common {
    prefix tailf;
  }

  identity dell-ftos {
    base ned:cli-ned-id;
  }
}
