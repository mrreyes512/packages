module tailf-ned-cisco-nx-id {
  // Generated by yanger -t ncs
  tailf:ncs-device-type "cli-ned";

  namespace "http://tail-f.com/ned/cisco-nx-id";
  prefix cisco-nx-id;

  import tailf-ncs-ned {
    prefix ned;
  }
  import tailf-ncs {
    prefix ncs;
  }
  import tailf-common {
    prefix tailf;
  }

  identity cisco-nx {
    base ned:cli-ned-id;
  }
}
