module tailf-ned-a10-acos {
  // Generated by yanger -t ncs
  tailf:ncs-device-type "cli-ned";

  namespace "http://tail-f.com/ned/a10-acos";
  prefix a10-acos;

  import tailf-common {
    prefix tailf;
  }
  import ietf-inet-types {
    prefix inet;
  }
  import tailf-ncs {
    prefix ncs;
  }

  revision 2017-02-28 {
    description
      "3.0.2.1
       Fixed build.xml to compile torwards Java 1.6.";
  }

  augment "/ncs:devices/ncs:device/ncs:config" {
    container vrrp-a {
      tailf:ncs-device-type "cli-ned";
      tailf:display-when "not(../../ncs:module) or ../../ncs:module[ncs:name='tailf-ned-a10-acos']";
      tailf:info
        "HA VRRP Global Commands";
      leaf device-id {
        tailf:info
          "Unique ID for each VRRP box";
        type uint8 {
          range "1..4";
          tailf:info
            "<1-4>;;device id";
        }
      }
      leaf disable-default-vrid {
        tailf:info
          "Disable default vrid";
        type empty;
      }
      leaf enable {
        tailf:info
          "Enable vrrp HA";
        type empty;
      }
      leaf set-id {
        tailf:info
          "Set-ID for HA configuration";
        type uint8 {
          range "1..7";
          tailf:info
            "<1-7>;;set id from 1 to 7";
        }
      }
      list vrid {
        tailf:info
          "VRRP id";
        key "id";
        leaf id {
          type union {
            type uint8 {
              range "1..31";
              tailf:info
                "<1-31>;;Specify ha VRRP vrid";
            }
            type enumeration {
              enum "default" {
                tailf:info
                  "Default VRRP vrid";
              }
            }
          }
        }
        leaf floating-ip {
          tailf:info
            "VRRP floating ip";
          type union {
            type inet:ipv4-address {
              tailf:info
                "A.B.C.D;;IP Address";
            }
            type inet:ipv6-address {
              tailf:info
                "A:B:C:D:E:F:G:H;;IPV6 address";
            }
          }
        }
        leaf priority {
          tailf:info
            "VRRP priorty";
          type uint8 {
            range "1..255";
            tailf:info
              "<1-255>;;Priority, default is 150";
          }
        }
        container preempt-mode {
          tailf:info
            "VRRP preempt";
          choice preempt-choice {
            leaf disable {
              tailf:info
                "disable preemption";
              type empty;
            }
            leaf threshhold {
              tailf:info
                "preemption threshhold";
              type uint8 {
                range "1..255";
                tailf:info
                  "<1..255>;;preemption threshhold (1-255), default 0";
              }
            }
          }
        }
        container tracking-options {
          tailf:info
            "VRRP tracking";
          tailf:cli-add-mode;

          grouping priority-cost {
            leaf priority-cost {
              tailf:info
                "The amount the priority will decrease";
              mandatory true;
              type uint8 {
                range "1..255";
                tailf:info
                  "<1-255>;;Priority";
              }
            }
          }
          list gateway {
            tailf:info
              "Gateway tracking";
            tailf:cli-suppress-mode;
            tailf:cli-incomplete-command;
            key "address";
            leaf address {
              type union {
                type inet:ipv4-address {
                  tailf:info
                    "A.B.C.D;;IP Address";
                }
                type inet:ipv6-address {
                  tailf:info
                    "A:B:C:D:E:F:G:H;;IPV6 address";
                }
              }
            }
            uses priority-cost;
          }
          container interface {
            tailf:info
              "Interface tracking";
            list ethernet {
              tailf:info
                "Ehternet Interface";
              tailf:cli-suppress-mode;
              tailf:cli-incomplete-command;
              key "id";
              leaf id {
                type leafref {
                  path "/ncs:devices/ncs:device/ncs:config/interface/ethernet/nr" {
                    tailf:xpath-root 3;
                  }
                }
              }
              uses priority-cost;
            }
          }
          list route {
            tailf:info
              "Route tracking";
            tailf:cli-suppress-mode;
            tailf:cli-compact-syntax;
            tailf:cli-remove-before-change;
            key "ip mask";
            leaf ip {
              type union {
                type inet:ipv4-address {
                  tailf:info
                    "A.B.C.D;;Destination prefix";
                }
                type inet:ipv6-address {
                  tailf:info
                    "A:B:C:D:E:F:G:H;;IPv6 destination prefix";
                }
              }
            }
            leaf mask {
              type inet:ipv4-address {
                tailf:info
                  "A.B.C.D;;Netmask";
              }
            }
            uses priority-cost;
            leaf distance {
              tailf:info
                "Route's administrative distance (default: match any)";
              type uint8 {
                range "1..255";
                tailf:info
                  "<1-255>;;The administrative distance for the route";
              }
            }
            leaf gateway {
              tailf:info
                "Match the route's gateway (next-hop) (default: match any)";
              type union {
                type inet:ipv4-address {
                  tailf:info
                    "A.B.C.D;;Forwarding router's address";
                }
                type inet:ipv6-address {
                  tailf:info
                    "A:B:C:D:E:F:G:H;;Match IPv6 Route Nexthop";
                }
              }
            }
            leaf protocol {
              tailf:info
                "The route protocol (default: match any)";
              type enumeration {
                enum "any" {
                  tailf:info
                    "Match any routing protocol (default)";
                }
                enum "static" {
                  tailf:info
                    "Match only static routes (added by user)";
                }
                enum "dynamic" {
                  tailf:info
                    "Match routes added by dynamic routing protocols (e.g. OSPF)";
                }
              }
            }
          }
          list trunk {
            tailf:info
              "trunk tracking";
            tailf:cli-suppress-mode;
            key "id";
            leaf id {
              type uint8 {
                range "1..16";
                tailf:info
                  "<1-16>;;Trunk Number";
              }
            }
            uses priority-cost;
          }
          list vlan {
            tailf:info
              "VLAN tracking";
            tailf:cli-suppress-mode;
            tailf:cli-sequence-commands;
            tailf:cli-compact-syntax;
            key "id";
            leaf id {
              type leafref {
                path "/ncs:devices/ncs:device/ncs:config/vlan/id" {
                  tailf:xpath-root 3;
                }
              }
            }
            leaf timeout {
              tailf:info
                "timeout";
              type uint16 {
                range "2..600";
                tailf:info
                  "<2-600>;;Timeout between 2 and 600 seconds (30 seconds suggested)";
              }
            }
            uses priority-cost;
          }
        }
      }
      container interface {
        tailf:info
          "VRRP Interface";
        list ethernet {
          tailf:cli-suppress-mode;
          tailf:info
            "Ethernet Interface";
          tailf:cli-compact-syntax;
          key "id";
          leaf id {
            type leafref {
              path "/ncs:devices/ncs:device/ncs:config/interface/ethernet/nr" {
                tailf:xpath-root 3;
              }
            }
          }
          choice vrrp-a-ethernet-choice {
            leaf both {
              tailf:info
                "both a router and server interface";
              type empty;
            }
            leaf no-heartbeat {
              tailf:info
                "do not send out heartbeat packet from this interface";
              type empty;
            }
            container router-interface {
              tailf:info
                "interface to upstream router";
              choice vrrp-a-r-i-choice {
                leaf no-heartbeat {
                  tailf:info
                    "do not send out heartbeat packet from this interface";
                  type empty;
                }
                leaf vlan {
                  tailf:info
                    "vlan";
                  type uint16 {
                    range "1..4094";
                    tailf:info
                      "<1-4094>;;vlan";
                  }
                }
              }
            }
            container server-interface {
              tailf:info
                "interface to real server";
              presence "true";
              choice vrrp-a-s-i-choice {
                leaf no-heartbeat {
                  tailf:info
                    "do not send out heartbeat packet from this interface";
                  type empty;
                }
                leaf vlan {
                  tailf:info
                    "vlan";
                  type uint16 {
                    range "1..4094";
                    tailf:info
                      "<1-4094>;;vlan";
                  }
                }
              }
            }
            leaf vlan {
              tailf:info
                "vlan";
              type uint16 {
                range "1..4094";
                tailf:info
                  "<1-4094>;;vlan";
              }
            }
          }
        }
      }
    }
    container ha {
      tailf:ncs-device-type "cli-ned";
      tailf:display-when "not(../../ncs:module) or ../../ncs:module[ncs:name='tailf-ned-a10-acos']";
      tailf:info
        "HA Global Commands";
      leaf arp-retry {
        tailf:info
          "Number of additional gratuitous ARPs sent out after HA failover";
        tailf:cli-full-command;
        type uint16 {
          range "1..255";
        }
      }
      container check {
        tailf:info
          "addtional things to check ha status";
        leaf gateway {
          tailf:info
            "Check gateway status";
          tailf:cli-full-command;
          type inet:ipv4-address {
            tailf:info
              "A.B.C.D;;ip address";
          }
        }
        list route {
          tailf:info
            "Check route status";
          key "ip mask gateway distance priority-cost";
          tailf:cli-compact-syntax;
          leaf ip {
            type union {
              type inet:ipv4-address {
                tailf:info
                  "A.B.C.D;;Destination prefix";
              }
              type inet:ipv6-address {
                tailf:info
                  "A:B:C:D:E:F:G:H;;Match IPv6 Route Nexthop";
              }
            }
          }
          leaf mask {
            type inet:ipv4-address {
              tailf:info
                "A.B.C.D;;Destination prefix mask";
            }
          }
          leaf gateway {
            tailf:info
              "Match the route's gateway (next-hop) (default: match any)";
            tailf:cli-expose-key-name;
            type union {
              type inet:ipv4-address {
                tailf:info
                  "A.B.C.D;;Forwarding router's address";
              }
              type inet:ipv6-address {
                tailf:info
                  "A:B:C:D:E:F:G:H;;Match IPv6 Route Nexthop";
              }
            }
          }
          leaf distance {
            tailf:info
              "Route's administrative distance (default: match any)";
            tailf:cli-expose-key-name;
            type uint8 {
              range "1..255";
              tailf:info
                "<1-255>;;The administrative distance for the route";
            }
          }
          leaf protocol {
            tailf:info
              "The route protocol (default: match any)";
            tailf:cli-expose-key-name;
            type enumeration {
              enum "any" {
                tailf:info
                  "Match any routing protocol (default)";
              }
              enum "static" {
                tailf:info
                  "Match only static routes (added by user)";
              }
              enum "dynamic" {
                tailf:info
                  "Match routes added by dynamic routing protocols (e.g. OSPF)";
              }
            }
            default "any";
          }
          leaf priority-cost {
            tailf:cli-expose-key-name;
            type uint8 {
              range "1..255";
              tailf:info
                "<1-255>;;The amount the priority will decrease if the route is not present";
            }
          }
        }
        container vlan {
          tailf:info
            "Check vlan status";
          tailf:cli-sequence-commands;
          tailf:cli-compact-syntax;
          leaf vlan-id {
            tailf:cli-drop-node-name;
            tailf:cli-incomplete-command;
            type uint16 {
              range "2..4094";
              tailf:info
                "<2-4094>;;VLAN id";
            }
          }
          leaf timeout {
            must "../vlan-id" {
              tailf:xpath-root 3;
              tailf:dependency "../vlan-id";
            }
            type uint16 {
              range "2..600" {
                tailf:info
                  "<2-600>;;Timeout between 2 and 600 seconds (30 seconds suggested)";
              }
            }
          }
        }
      }
      container conn-mirror {
        tailf:info
          "Enable HA Connection Mirroring";
        leaf ip {
          tailf:info
            "ip address to mirror to";
          type inet:ipv4-address {
            tailf:info
              "A.B.C.D;;ip address";
          }
        }
      }
      container force-self-standby {
        tailf:info
          "Force the unit or a group to HA standby state";
        presence "true";
        tailf:cli-reset-container;
        leaf HA-group-id {
          tailf:info
            "HA group id to force in HA standby state";
          type uint16 {
            range "1..31" {
              tailf:info
                "<1-31>;;HA group id from 1 to 31";
            }
          }
        }
      }
      leaf forward-l4-packet-on-standby {
        tailf:info
          "HA Enable standby AX to do l2/l3 forward of l4 packets";
        tailf:cli-full-command;
        type empty;
      }
      list group {
        tailf:info
          "HA Group";
        tailf:cli-suppress-mode;
        key "id";
        tailf:cli-sequence-commands;
        tailf:cli-compact-syntax;
        tailf:cli-incomplete-command;
        leaf id {
          type uint16 {
            range "1..31";
          }
        }
        leaf priority {
          tailf:info
            "HA group priority";
          must "../id" {
            tailf:xpath-root 3;
            tailf:dependency "../id";
          }
          type uint16 {
            range "1..255";
          }
        }
      }
      container id {
        tailf:info
          "Unique ID for each HA box";
        tailf:cli-sequence-commands;
        tailf:cli-compact-syntax;
        leaf id {
          tailf:cli-drop-node-name;
          type uint8;
        }
        leaf set-id {
          must "../id" {
            tailf:xpath-root 3;
            tailf:dependency "../id";
          }
          type uint8 {
            range "1..7";
          }
        }
      }
      container inline-mode {
        tailf:info
          "Enable Layer2 Inline Hot Standby Mode";
        presence "true";
        tailf:cli-reset-container;
        leaf preferred-port {
          tailf:info
            "Preferred port";
          type uint8;
        }
      }
      container interface {
        tailf:info
          "HA interface";
        list ethernet {
          tailf:info
            "Etherenet interface";
          tailf:cli-suppress-mode;
          tailf:cli-compact-syntax;
          key "id";
          leaf id {
            type uint8;
          }
          leaf type {
            tailf:cli-drop-node-name;
            tailf:cli-reset-container;
            type enumeration {
              enum "both" {
                tailf:info
                  "both a router and server interface";
              }
              enum "router-interface" {
                tailf:info
                  "interface to upstream router";
              }
              enum "server-interface" {
                tailf:info
                  "interface to real server";
              }
            }
          }
          choice xx {
            leaf no-heartbeat {
              tailf:cli-reset-container;
              tailf:cli-full-command;
              tailf:info
                "do not send out heartbeat packet from this interface";
              type empty;
            }
            leaf vlan {
              tailf:cli-reset-container;
              tailf:cli-full-command;
              type uint16 {
                range "1..4094";
                tailf:info
                  "<1-4094>;;vlan";
              }
            }
          }
        }
      }
      leaf preemption-enable {
        tailf:info
          "HA Enable failover preemption based on priority";
        tailf:cli-full-command;
        type empty;
      }
    }
    leaf hostname {
      tailf:ncs-device-type "cli-ned";
      tailf:display-when "not(../../ncs:module) or ../../ncs:module[ncs:name='tailf-ned-a10-acos']";
      tailf:info
        "Set system's network name";
      tailf:cli-full-command;
      type string {
        length "1..31";
        tailf:info
          "WORD<length:1-31>;;This System's Network Name";
      }
    }
    container clock {
      tailf:ncs-device-type "cli-ned";
      tailf:display-when "not(../../ncs:module) or ../../ncs:module[ncs:name='tailf-ned-a10-acos']";
      tailf:info
        "Configure time-of-day Clock";
      leaf timezone {
        tailf:info
          "Configure the Time Zone";
        type enumeration {
          enum "Pacific/Midway" {
            tailf:info
              "(GMT-11:00)Midway Island, Samoa";
          }
          enum "Pacific/Honolulu" {
            tailf:info
              "(GMT-10:00)Hawaii";
          }
          enum "America/Anchorage" {
            tailf:info
              "(GMT-09:00)Alaska";
          }
          enum "America/Tijuana" {
            tailf:info
              "(GMT-08:00)Pacific Time - Tijuana";
          }
          enum "America/Los_Angeles" {
            tailf:info
              "(GMT-08:00)Pacific Time(US & Canada)";
          }
          enum "America/Vancouver" {
            tailf:info
              "(GMT-08:00)Pacific Time - west British Columbia";
          }
          enum "America/Phoenix" {
            tailf:info
              "(GMT-07:00)Arizona";
          }
          enum "America/Shiprock" {
            tailf:info
              "(GMT-07:00)Mountain Time(US & Canada)";
          }
          enum "America/Chicago" {
            tailf:info
              "(GMT-06:00)Central Time(US & Canada)";
          }
          enum "America/Mexico_City" {
            tailf:info
              "(GMT-06:00)Mexico City";
          }
          enum "America/Regina" {
            tailf:info
              "(GMT-06:00)Saskatchewan";
          }
          enum "America/Swift_Current" {
            tailf:info
              "(GMT-06:00)Central America";
          }
          enum "America/Kentucky/Monticello" {
            tailf:info
              "(GMT-05:00)Eastern Time(US & Canada)";
          }
          enum "America/Indiana/Marengo" {
            tailf:info
              "(GMT-05:00)Indiana(East)";
          }
          enum "America/Montreal" {
            tailf:info
              "(GMT-05:00)Eastern Time - Ontario & Quebec - most locations";
          }
          enum "America/New_York" {
            tailf:info
              "(GMT-05:00)Eastern Time";
          }
          enum "America/Toronto" {
            tailf:info
              "(GMT-05:00)Eastern Time - Toronto, Ontario";
          }
          enum "America/Caracas" {
            tailf:info
              "(GMT-04:00)Caracas, La Paz";
          }
          enum "America/Halifax" {
            tailf:info
              "(GMT-04:00)Atlantic Time(Canada)";
          }
          enum "America/Santiago" {
            tailf:info
              "(GMT-04:00)Santiago";
          }
          enum "America/St_Johns" {
            tailf:info
              "(GMT-03:30)Newfoundland";
          }
          enum "America/Buenos_Aires" {
            tailf:info
              "(GMT-03:00)Buenos Aires, Georgetown";
          }
          enum "America/Godthab" {
            tailf:info
              "(GMT-03:00)Greenland";
          }
          enum "Atlantic/South_Georgia" {
            tailf:info
              "(GMT-02:00)Mid-Atlantic";
          }
          enum "Atlantic/Azores" {
            tailf:info
              "(GMT-01:00)Azores";
          }
          enum "Atlantic/Cape_Verde" {
            tailf:info
              "(GMT-01:00)Cape Verde Is.";
          }
          enum "Europe/Dublin" {
            tailf:info
              "(GMT)Greenwich Mean Time: Dublin, Edinburgh, Lisbon, London";
          }
          enum "Africa/Algiers" {
            tailf:info
              "(GMT+01:00)West Central Africa";
          }
          enum "Europe/Amsterdam" {
            tailf:info
              "(GMT+01:00)Amsterdam, Berlin, Bern, Rome, Stockholm, Vienna";
          }
          enum "Europe/Belgrade" {
            tailf:info
              "(GMT+01:00)Belgrade, Bratislava, Budapest, Ljubljana, Prague";
          }
          enum "Europe/Brussels" {
            tailf:info
              "(GMT+01:00)Brussels, Copenhagen, Madrid, Paris";
          }
          enum "Europe/Sarajevo" {
            tailf:info
              "(GMT+01:00)Sarajevo, Skopje, Sofija, Vilnius, Warsaw, Zagreb";
          }
          enum "Europe/Bucharest" {
            tailf:info
              "(GMT+02:00)Bucharest";
          }
          enum "Africa/Cairo" {
            tailf:info
              "(GMT+02:00)Cairo";
          }
          enum "Europe/Athens" {
            tailf:info
              "(GMT+02:00)Athens, Istanbul, Minsk";
          }
          enum "Africa/Harare" {
            tailf:info
              "(GMT+02:00)Harare, Pretoria";
          }
          enum "Asia/Jerusalem" {
            tailf:info
              "(GMT+02:00)Jerusalem";
          }
          enum "Europe/Helsinki" {
            tailf:info
              "(GMT+02:00)Helsinki, Riga, Tallinn";
          }
          enum "Africa/Nairobi" {
            tailf:info
              "(GMT+03:00)Nairobi";
          }
          enum "Asia/Baghdad" {
            tailf:info
              "(GMT+03:00)Baghdad";
          }
          enum "Asia/Kuwait" {
            tailf:info
              "(GMT+03:00)Kuwait, Riyadh";
          }
          enum "Europe/Moscow" {
            tailf:info
              "(GMT+03:00)Moscow, St.Petersburg, Volgogard";
          }
          enum "Asia/Tehran" {
            tailf:info
              "(GMT+03:30)Tehran";
          }
          enum "Asia/Baku" {
            tailf:info
              "(GMT+04:00)Baku, Tbilisi, Yerevan";
          }
          enum "Asia/Muscat" {
            tailf:info
              "(GMT+04:00)Abu Dhabi, Muscat";
          }
          enum "Asia/Kabul" {
            tailf:info
              "(GMT+04:30)Kabul";
          }
          enum "Asia/Karachi" {
            tailf:info
              "(GMT+05:00)Islamabad, Karachi, Tashkent";
          }
          enum "Asia/Yekaterinburg" {
            tailf:info
              "(GMT+05:00)Ekaterinburg";
          }
          enum "Asia/Calcutta" {
            tailf:info
              "(GMT+05:30)Calcutta, Chennai, Mumbai, New Delhi";
          }
          enum "Asia/Katmandu" {
            tailf:info
              "(GMT+05:45)Kathmandu";
          }
          enum "Asia/Almaty" {
            tailf:info
              "(GMT+06:00)Almaty, Novosibirsk";
          }
          enum "Asia/Dhaka" {
            tailf:info
              "(GMT+06:00)Astana, Dhaka";
          }
          enum "Indian/Chagos" {
            tailf:info
              "(GMT+06:00)Sri Jayawardenepura";
          }
          enum "Asia/Rangoon" {
            tailf:info
              "(GMT+06:30)Rangoon";
          }
          enum "Asia/Bangkok" {
            tailf:info
              "(GMT+07:00)Bangkok, Hanoi, Jakarta";
          }
          enum "Asia/Krasnoyarsk" {
            tailf:info
              "(GMT+07:00)Krasnoyarsk";
          }
          enum "Asia/Irkutsk" {
            tailf:info
              "(GMT+08:00)Irkutsk, Ulaan Bataar";
          }
          enum "Asia/Kuala_Lumpur" {
            tailf:info
              "(GMT+08:00)Kuala Lumpur, Singapore";
          }
          enum "Asia/Shanghai" {
            tailf:info
              "(GMT+08:00)Beijing, Chongqing, Hong Kong, Urumqi";
          }
          enum "Asia/Taipei" {
            tailf:info
              "(GMT+08:00)Taipei";
          }
          enum "Australia/Perth" {
            tailf:info
              "(GMT+08:00)Perth";
          }
          enum "Asia/Seoul" {
            tailf:info
              "(GMT+09:00)Seoul";
          }
          enum "Asia/Tokyo" {
            tailf:info
              "(GMT+09:00)Osaka, Sapporo, Tokyo";
          }
          enum "Asia/Yakutsk" {
            tailf:info
              "(GMT+09:00)Yakutsk";
          }
          enum "Australia/Adelaide" {
            tailf:info
              "(GMT+09:30)Adelaide";
          }
          enum "Australia/Darwin" {
            tailf:info
              "(GMT+09:30)Darwin";
          }
          enum "Australia/Hobart" {
            tailf:info
              "(GMT+10:00)Hobart";
          }
          enum "Australia/Brisbane" {
            tailf:info
              "(GMT+10:00)Brisbane";
          }
          enum "Asia/Vladivostok" {
            tailf:info
              "(GMT+10:00)Vladivostok";
          }
          enum "Australia/Sydney" {
            tailf:info
              "(GMT+10:00)Canberra, Melbourne, Sydney";
          }
          enum "Pacific/Guam" {
            tailf:info
              "(GMT+10:00)Guam, Port Moresby";
          }
          enum "Asia/Magadan" {
            tailf:info
              "(GMT+11:00)Magadan, Solomon., New Caledonia";
          }
          enum "Pacific/Auckland" {
            tailf:info
              "(GMT+12:00)Auckland, Wellington";
          }
          enum "Pacific/Fiji" {
            tailf:info
              "(GMT+12:00)Fiji, Kamchatka, Marshall Is.";
          }
          enum "Pacific/Kwajalein" {
            tailf:info
              "(GMT+12:00)Eniwetok, Kwajalein";
          }
          enum "Pacific/Enderbury" {
            tailf:info
              "(GMT+13:00)Nuku'alofa";
          }
        }
      }
    }
    container ntp {
      tailf:ncs-device-type "cli-ned";
      tailf:display-when "not(../../ncs:module) or ../../ncs:module[ncs:name='tailf-ned-a10-acos']";
      tailf:info
        "Network Time Protocol configuration";
      list server {
        tailf:cli-suppress-mode;
        tailf:info
          "Set NTP time server";
        tailf:cli-sequence-commands;
        tailf:cli-compact-syntax;
        key "name";
        leaf name {
          type string {
            tailf:info
              "Hostname or A.B.C.D or A:B:C:D:E:F:G:H";
          }
        }
        leaf interval {
          tailf:cli-drop-node-name;
          type uint32;
        }
      }
    }
    container system {
      tailf:ncs-device-type "cli-ned";
      tailf:display-when "not(../../ncs:module) or ../../ncs:module[ncs:name='tailf-ned-a10-acos']";
      tailf:info
        "Configure System Parameters";
      leaf module-ctrl-cpu {
        tailf:info
          "System module control CPU usage setting";
        type enumeration {
          enum "high" {
            tailf:info
              "high cpu usage";
          }
          enum "low" {
            tailf:info
              "low cpu usage";
          }
          enum "medium" {
            tailf:info
              "medium cpu usage";
          }
        }
      }
      leaf glid {
        tailf:info
          "Apply limits to the whole system";
        tailf:cli-full-command;
        type uint16 {
          range "1..1023";
          tailf:info
            "<1-1023>;;Specify a limit ID";
        }
      }
      container all-vlan-limit {
        tailf:info
          "all vlan flooding packet limit";
        leaf bcast {
          tailf:info
            "broadcast packets";
          tailf:cli-full-command;
          type uint16 {
            range "1..65535";
            tailf:info
              "<1-65535>;;per second limit";
          }
        }
        leaf ipmcast {
          tailf:info
            "IP multicast packets";
          tailf:cli-full-command;
          type uint16 {
            range "1..65535";
            tailf:info
              "<1-65535>;;per second limit";
          }
        }
        leaf mcast {
          tailf:info
            "multicast packets";
          tailf:cli-full-command;
          type uint16 {
            range "1..65535";
            tailf:info
              "<1-65535>;;per second limit";
          }
        }
        leaf unknown-ucast {
          tailf:info
            "unknown unicast packets";
          tailf:cli-full-command;
          type uint16 {
            range "1..65535";
            tailf:info
              "<1-65535>;;per second limit";
          }
        }
      }
      container per-vlan-limit {
        tailf:info
          "per vlan flooding packet limit";
        leaf bcast {
          tailf:info
            "broadcast packets";
          tailf:cli-full-command;
          type uint16 {
            range "1..65535";
            tailf:info
              "<1-65535>;;per second limit";
          }
        }
        leaf ipmcast {
          tailf:info
            "IP multicast packets";
          tailf:cli-full-command;
          type uint16 {
            range "1..65535";
            tailf:info
              "<1-65535>;;per second limit";
          }
        }
        leaf mcast {
          tailf:info
            "multicast packets";
          tailf:cli-full-command;
          type uint16 {
            range "1..65535";
            tailf:info
              "<1-65535>;;per second limit";
          }
        }
        leaf unknown-ucast {
          tailf:info
            "unknown unicast packets";
          tailf:cli-full-command;
          type uint16 {
            range "1..65535";
            tailf:info
              "<1-65535>;;per second limit";
          }
        }
      }
      container resource-usage {
        tailf:info
          "Configure System Resource Usage";
        leaf class-list-ipv6-addr-count {
          tailf:cli-full-command;
          tailf:info
            "Total IPv6 addresses for class-list";
          type uint32 {
            range "1..8192000";
            tailf:info
              "<1-8192000>;;Total IPv6 addresses for class-list";
          }
        }
        leaf client-ssl-template-count {
          tailf:info
            "Total configurable Client SSL Templates in the System";
          tailf:cli-full-command;
          type uint32 {
            range "32..16384";
            tailf:info
              "<32-16384>;;Total configurable Client SSL Templates in the System";
          }
        }
        leaf conn-reuse-template-count {
          tailf:info
            "Total configurable Connection reuse Templates in the System";
          tailf:cli-full-command;
          type uint32 {
            range "32..8192";
            tailf:info
              "<32-8192>;;Total configurable Connection reuse Templates in the System";
          }
        }
        leaf fast-tcp-template-count {
          tailf:info
            "Total configurable Fast TCP Templates in the System";
          tailf:cli-full-command;
          type uint32 {
            range "32..8192";
            tailf:info
              "<32-8192>;;Total configurable Fast TCP Templates in the System";
          }
        }
        leaf fast-udp-template-count {
          tailf:info
            "Total configurable Fast UDP Templates in the System";
          tailf:cli-full-command;
          type uint32 {
            range "32..8192";
            tailf:info
              "<32-8192>;;Total configurable Fast UDP Templates in the System";
          }
        }
        leaf http-template-count {
          tailf:info
            "Total configurable HTTP Templates in the System";
          tailf:cli-full-command;
          type uint32 {
            range "32..8192";
            tailf:info
              "<32-8192>;;Total configurable HTTP Templates in the System";
          }
        }
        leaf l4-session-count {
          tailf:info
            "Total Sessions in the System";
          tailf:cli-full-command;
          type uint32 {
            range "131072..134217728";
            tailf:info
              "<131072-134217728>;;Total Sessions in the System";
          }
        }
        leaf nat-pool-addr-count {
          tailf:info
            "Total configurable NAT Pool addresses in the System";
          tailf:cli-full-command;
          type uint32 {
            range "10..4000";
            tailf:info
              "<10-4000>;;Total configurable NAT pool addresses in the System";
          }
        }
        leaf persist-cookie-template-count {
          tailf:info
            "Total configurable Persistent cookie Templates in the System";
          tailf:cli-full-command;
          type uint32 {
            range "32..8192";
            tailf:info
              "<32-8192>;;Total configurable Persistent cookie Templates in the System";
          }
        }
        leaf persist-srcip-template-count {
          tailf:info
            "Total configurable Source IP Persistent Templates in the System";
          tailf:cli-full-command;
          type uint32 {
            range "32..8192";
            tailf:info
              "<32-8192>;;Total configurable Source IP Persistent Templates in the System";
          }
        }
        leaf proxy-template-count {
          tailf:info
            "Total configurable Proxy Templates in the System";
          tailf:cli-full-command;
          type uint32 {
            range "32..8192";
            tailf:info
              "<32-8192>;;Total configurable Proxy Templates in the System";
          }
        }
        leaf real-port-count {
          tailf:info
            "Total Real Server Ports in the System";
          tailf:cli-full-command;
          type uint32 {
            range "512..32768";
            tailf:info
              "<512-32768>;;Total Real Server Ports in the System";
          }
        }
        leaf real-server-count {
          tailf:info
            "Total Real Servers in the System";
          tailf:cli-full-command;
          type uint32 {
            range "512..16384";
            tailf:info
              "<512-16384>;;Total Real Servers in the System";
          }
        }
        leaf server-ssl-template-count {
          tailf:info
            "Total configurable Server SSL Templates in the System";
          tailf:cli-full-command;
          type uint32 {
            range "32..16384";
            tailf:info
              "<32-16384>;;Total configurable Server SSL Templates bin the System";
          }
        }
        leaf service-group-count {
          tailf:info
            "Total Service Groups in the System";
          tailf:cli-full-command;
          type uint32 {
            range "512..16384";
            tailf:info
              "<512-16384>;;Total Service Groups in the System";
          }
        }
        leaf stream-template-count {
          tailf:info
            "Total configurable Streaming media in the System";
          tailf:cli-full-command;
          type uint32 {
            range "32..8192";
            tailf:info
              "<32-8192>;;Total configurable Streaming media in the System";
          }
        }
        leaf virtual-port-count {
          tailf:info
            "Total Virtual Server Ports in the System";
          tailf:cli-full-command;
          type uint32 {
            range "256..16384";
            tailf:info
              "<256-16384>;;Total Virtual Server Ports in the System";
          }
        }
        leaf virtual-server-count {
          tailf:info
            "Total Virtual Servers in the System";
          tailf:cli-full-command;
          type uint32 {
            range "512..8192";
            tailf:info
              "<512-8192>;;Total Virtual Servers in the System";
          }
        }
      }
      container template {
        tailf:info
          "Apply template to the whole system";
        leaf policy {
          type string {
            tailf:info
              "NAME<length:1-63>;;Policy template name";
            length "1..63";
          }
        }
      }
      leaf ve-mac-scheme {
        tailf:info
          "VE MAC allocation scheme";
        type enumeration {
          enum "hash-based" {
            tailf:info
              "Hash-based using the VE number";
          }
          enum "round-robin" {
            tailf:info
              "Round Robin scheme";
          }
          enum "system-mac" {
            tailf:info
              "Use system MAC address";
          }
        }
      }
    }
    list trunk {
      tailf:ncs-device-type "cli-ned";
      tailf:display-when "not(../ncs:module) or ../ncs:module[ncs:name='tailf-ned-a10-acos']";
      tailf:info
        "Trunk Group Settings";
      key "id";
      tailf:cli-full-command;
      leaf id {
        type uint16 {
          range "1..16";
        }
      }
      container ethernet {
        tailf:info
          "Ethernet port";
        tailf:cli-sequence-commands;
        tailf:cli-compact-syntax;
        leaf from {
          tailf:cli-drop-node-name;
          type uint16;
        }
        leaf to {
          tailf:info
            "To an end range";
          must "../from" {
            tailf:xpath-root 3;
            tailf:dependency "../from";
          }
          type uint16;
        }
      }
      leaf port-threshold {
        tailf:info
          "Threshold for minimum number of ports that need to be UP";
        tailf:cli-full-command;
        type uint16 {
          range "2..8";
          tailf:info
            "<2-8>;;Number of ports";
        }
      }
      leaf port-threshold-timer {
        tailf:info
          "Timer for Ports-Threshold";
        tailf:cli-full-command;
        type uint16 {
          range "1..300";
          tailf:info
            "<1-300>;;Time in seconfd (default: 10)";
        }
        default "10";
      }
    }
    list vlan {
      tailf:ncs-device-type "cli-ned";
      tailf:display-when "not(../ncs:module) or ../ncs:module[ncs:name='tailf-ned-a10-acos']";
      tailf:info
        "Configure VLAN";
      key "id";
      tailf:cli-full-command;
      leaf id {
        type uint16 {
          range "2..4094";
          tailf:info
            "VLAN number";
        }
      }
      leaf name {
        tailf:info
          "VLAN name";
        tailf:cli-full-command;
        type string {
          length "1..63";
          tailf:info
            "WORD<length:1-63>;;VLAN name";
        }
      }
      container router-interface {
        tailf:info
          "router-interface";
        leaf ve {
          type uint16 {
            range "1..4094";
          }
        }
      }
      container untagged {
        tailf:info
          "untagged";
        tailf:cli-compact-syntax;
        container ethernet {
          tailf:info
            "Ethernet port";
          tailf:cli-sequence-commands;
          tailf:cli-compact-syntax;
          leaf from {
            tailf:cli-drop-node-name;
            type uint16;
          }
          leaf to {
            must "../from" {
              tailf:xpath-root 3;
              tailf:dependency "../from";
            }
            type uint16;
          }
        }
        leaf trunk {
          tailf:info
            "Trunk groups";
          tailf:cli-full-command;
          type uint8 {
            range "1..16";
          }
        }
      }
      container tagged {
        tailf:info
          "tagged";
        tailf:cli-compact-syntax;
        container ethernet {
          tailf:info
            "Etherenet port";
          tailf:cli-sequence-commands;
          tailf:cli-compact-syntax;
          leaf from {
            tailf:cli-drop-node-name;
            type uint16;
          }
          leaf to {
            must "../from" {
              tailf:xpath-root 3;
              tailf:dependency "../from";
            }
            type uint16;
          }
        }
        leaf trunk {
          tailf:info
            "Trunk groups";
          tailf:cli-full-command;
          type uint8 {
            range "1..16";
          }
        }
      }
    }
    list access-list {
      tailf:ncs-device-type "cli-ned";
      tailf:display-when "not(../ncs:module) or ../ncs:module[ncs:name='tailf-ned-a10-acos']";
      tailf:info
        "Configure Access List";
      tailf:cli-suppress-mode;
      key "id";
      leaf id {
        type uint16 {
          range "1..199";
        }
      }
      list rules {
        ordered-by user;
        tailf:cli-suppress-mode;
        tailf:cli-drop-node-name;
        tailf:cli-show-long-obu-diffs;
        key "txt";
        leaf txt {
          tailf:cli-multi-word-key;
          type string;
        }
      }
    }
    container radius-server {
      tailf:ncs-device-type "cli-ned";
      tailf:display-when "not(../../ncs:module) or ../../ncs:module[ncs:name='tailf-ned-a10-acos']";
      tailf:info
        "Configure RADIUS server information";
      list host {
        tailf:info
          "Specify the RADIUS server's hostname or IP address";
        tailf:cli-suppress-mode;
        tailf:cli-incomplete-command;
        tailf:cli-sequence-commands {
          tailf:cli-reset-siblings;
        }
        tailf:cli-compact-syntax;
        key "name";
        leaf name {
          type union {
            type string {
              tailf:info
                "Hostname or A.B.C.D;;The RADIUS server's hostname of IP address";
            }
            type inet:ipv6-address {
              tailf:info
                "A:B:C:D:E:F:G:H;;The RADIUS server's IPV6 address";
            }
          }
        }
        container secret {
          tailf:info
            "Specify the RADIUS server's secret";
          tailf:cli-flatten-container;
          tailf:cli-sequence-commands {
            tailf:cli-reset-siblings;
          }
          tailf:cli-compact-syntax;
          leaf cleartext {
            tailf:cli-drop-node-name;
            tailf:cli-disallow-value "encrypted";
            tailf:cli-optional-in-sequence;
            type string {
              tailf:info
                "WORD<length:0-31>  Password, '' means empty password";
              length "0..31";
            }
          }
          leaf secret-encrypted {
            when "not(../cleartext)" {
              tailf:xpath-root 3;
              tailf:dependency "../cleartext";
            }
            tailf:info
              "Do NOT use this option manually. (This is an A10 reserved  keyword.)";
            type string {
              length "1..255";
              tailf:info
                "WORD<length:1-255>;;The ENCRYPTED secret string";
            }
          }
        }
      }
    }
    container interface {
      tailf:ncs-device-type "cli-ned";
      tailf:display-when "not(../../ncs:module) or ../../ncs:module[ncs:name='tailf-ned-a10-acos']";
      tailf:info
        "Select an interface to configure";
      container management {
        tailf:info
          "Management interface";
        tailf:cli-add-mode;
        container ip {
          tailf:info
            "Global IP configuration subcommands";
          list address {
            key "ip";
            tailf:cli-suppress-mode;
            tailf:info
              "Set the IP address of an interface";
            tailf:cli-sequence-commands {
              tailf:cli-reset-siblings;
            }
            tailf:cli-compact-syntax;
            leaf ip {
              tailf:cli-drop-node-name;
              tailf:cli-incomplete-command;
              type inet:ipv4-address;
            }
            leaf mask {
              tailf:cli-drop-node-name;
              type inet:ipv4-address;
            }
          }
          leaf control-apps-use-mgmt-port {
            tailf:info
              "Control applications use management port";
            tailf:cli-full-command;
            type empty;
          }
          leaf default-gateway {
            tailf:info
              "Set default gateway";
            type inet:ipv4-address;
          }
        }
        container ipv6 {
          tailf:info
            "Global IP configuration subcommands";
          list address {
            key "ip";
            tailf:cli-suppress-mode;
            tailf:info
              "Set the IP address of an interface";
            tailf:cli-sequence-commands {
              tailf:cli-reset-siblings;
            }
            tailf:cli-compact-syntax;
            leaf ip {
              tailf:cli-drop-node-name;
              type inet:ipv6-prefix;
            }
            leaf link-local {
              type empty;
              tailf:info
                "Configure an IPv6 link local address";
            }
          }
          leaf default-gateway {
            tailf:info
              "Set default gateway";
            type inet:ipv6-address;
          }
        }
        leaf flow-control {
          tailf:info
            "Enable 802.3x flow control on full duplex port";
          tailf:cli-full-command;
          type empty;
        }
        container access-list {
          tailf:info
            "Apply ACL rules to incoming packets on this interface";
          tailf:cli-sequence-commands {
            tailf:cli-reset-siblings;
          }
          tailf:cli-compact-syntax;
          leaf id {
            tailf:cli-drop-node-name;
            tailf:cli-incomplete-command;
            type uint16 {
              range "1..199";
              tailf:info
                "<1-199>;;ACL id";
            }
          }
          leaf in {
            must "../id" {
              tailf:xpath-root 3;
              tailf:dependency "../id";
            }
            type empty;
            tailf:info
              "ACL applied on incoming packets to this interface";
          }
        }
        leaf enabled-disabled {
          tailf:cli-drop-node-name;
          tailf:cli-full-command;
          type enumeration {
            enum "enable" {
              tailf:info
                "Disable Interface";
            }
            enum "disable" {
              tailf:info
                "Enable Interface";
            }
          }
          default "enable";
        }
        leaf duplexity {
          tailf:cli-full-command;
          tailf:info
            "Interface Duplexity";
          type enumeration {
            enum "full" {
              tailf:info
                "Full Duplex";
            }
            enum "half" {
              tailf:info
                "Half Duplex";
            }
            enum "auto" {
              tailf:info
                "Auto Negotiate Duplexity";
            }
          }
          default "auto";
        }
        leaf mtu {
          tailf:cli-full-command;
          tailf:info
            "Interface mtu";
          type uint16 {
            range "1200..1500";
          }
          default "1500";
        }
        leaf speed {
          tailf:cli-full-command;
          type enumeration {
            enum "10" {
              tailf:info
                "10 Mbs/sec";
            }
            enum "100" {
              tailf:info
                "100 Mbs/sec";
            }
            enum "1000" {
              tailf:info
                "1 Gb/sec";
            }
            enum "auto" {
              tailf:info
                "Auto Negotiate Speed";
            }
          }
          default "auto";
        }
      }
      list ethernet {
        key "nr";
        leaf nr {
          type uint16 {
            range "1..20";
          }
        }
        container access-list {
          tailf:info
            "Apply ACL rules to incoming packets on this interface";
          tailf:cli-sequence-commands {
            tailf:cli-reset-siblings;
          }
          tailf:cli-compact-syntax;
          leaf id {
            tailf:cli-drop-node-name;
            tailf:cli-incomplete-command;
            type uint16 {
              range "1..199";
              tailf:info
                "<1-199>;;ACL id";
            }
          }
          leaf in {
            must "../id" {
              tailf:xpath-root 3;
              tailf:dependency "../id";
            }
            type empty;
            tailf:info
              "ACL applied on incoming packets to this interface";
          }
        }
        leaf enabled-disabled {
          tailf:cli-drop-node-name;
          tailf:cli-full-command;
          type enumeration {
            enum "enable" {
              tailf:info
                "Disable Interface";
            }
            enum "disable" {
              tailf:info
                "Enable Interface";
            }
          }
          default "enable";
        }
        leaf duplexity {
          tailf:cli-full-command;
          tailf:info
            "Interface Duplexity";
          type enumeration {
            enum "full" {
              tailf:info
                "Full Duplex";
            }
            enum "half" {
              tailf:info
                "Half Duplex";
            }
            enum "auto" {
              tailf:info
                "Auto Negotiate Duplexity";
            }
          }
          default "auto";
        }
        leaf flow-control {
          tailf:info
            "Enable 802.3x flow control on full duplex port";
          tailf:cli-full-command;
          type empty;
        }
        container icmp-rate-limit {
          tailf:cli-sequence-commands {
            tailf:cli-reset-siblings;
          }
          tailf:cli-compact-syntax;
          tailf:info
            "Limit ICMP traffic to this interface";
          leaf rate {
            tailf:cli-drop-node-name;
            type uint16 {
              range "1..65535";
              tailf:info
                "<1-65535>;;Normal rate limit. If exceeds this limit, drop the ICMP packet that goes over the limit";
            }
          }
          leaf lockup {
            must "../rate" {
              tailf:xpath-root 3;
              tailf:dependency "../rate";
            }
            tailf:info
              "Enter lockup state when ICMP rate exceeds lockup rate limit";
            type uint16 {
              range "1..65535";
              tailf:info
                "<1-65535>;;Maximum rate limit. If exceeds this limit, drop all ICMP packet for a time period";
            }
            tailf:cli-incomplete-command;
          }
          leaf lockup-perio {
            must "../lockup" {
              tailf:xpath-root 3;
              tailf:dependency "../lockup";
            }
            tailf:cli-drop-node-name;
            type uint16 {
              range "1..65535";
              tailf:info
                "Lockup period (second)";
            }
          }
        }
        container ip {
          tailf:info
            "Global IP configuration subcommands";
          list address {
            key "ip";
            tailf:cli-suppress-mode;
            tailf:info
              "Set the IP address of an interface";
            tailf:cli-sequence-commands {
              tailf:cli-reset-siblings;
            }
            tailf:cli-compact-syntax;
            leaf ip {
              tailf:cli-drop-node-name;
              tailf:cli-incomplete-command;
              type inet:ipv4-address;
            }
            leaf mask {
              must "../ip" {
                tailf:xpath-root 3;
                tailf:dependency "../ip";
              }
              tailf:cli-drop-node-name;
              type inet:ipv4-address;
            }
          }
          leaf allow-promiscuous-vip {
            tailf:info
              "Allow traffic to be associated with promiscuous VIP";
            tailf:cli-full-command;
            type empty;
          }
          leaf cache-spoofing-port {
            tailf:info
              "This interface connects to spoofing cache";
            tailf:cli-full-command;
            type empty;
          }
          leaf helper-address {
            tailf:info
              "Helper address for DHCP packets";
            tailf:cli-full-command;
            type inet:ipv4-address;
          }
          container nat {
            tailf:info
              "Enable NAT on the interface";
            leaf inside {
              tailf:info
                "Configure interface as inside";
              tailf:cli-full-command;
              type empty;
            }
            leaf outside {
              tailf:info
                "Configure interface as outside";
              tailf:cli-full-command;
              type empty;
            }
          }
          container ospf;
          container router {
            tailf:info
              "Router";
            container isis {
              tailf:info
                "IS-IS Routing for IP";
              presence "true";
              tailf:cli-reset-container;
              leaf cmds {
                tailf:cli-drop-node-name;
                type string {
                  length "1..255";
                  tailf:info
                    "WORD<length:1-255>;;Specify interface route cmds";
                }
              }
            }
          }
          container tcp {
            tailf:info
              "TCP parameters";
            leaf syn-cookie {
              tailf:info
                "Enable TCP syn-cookie";
              type empty;
            }
          }
        }
        container ipv6 {
          tailf:info
            "Global IP configuration subcommands";
          container access-list {
            tailf:info
              "Apply ACL rules to incoming packets on this interface";
            tailf:cli-sequence-commands {
              tailf:cli-reset-siblings;
            }
            tailf:cli-compact-syntax;
            leaf id {
              tailf:cli-drop-node-name;
              tailf:cli-incomplete-command;
              type string {
                length "1..16";
                tailf:info
                  "WORD<length:1-16>;;Named Access List";
              }
            }
            leaf in {
              must "../id" {
                tailf:xpath-root 3;
                tailf:dependency "../id";
              }
              type empty;
              tailf:info
                "ACL applied on incoming packets to this interface";
            }
          }
          list address {
            key "ip";
            tailf:cli-suppress-mode;
            tailf:info
              "Set the IP address of an interface";
            tailf:cli-sequence-commands {
              tailf:cli-reset-all-siblings;
            }
            tailf:cli-compact-syntax;
            leaf ip {
              tailf:cli-drop-node-name;
              type inet:ipv6-prefix;
            }
            leaf link-local {
              type empty;
              tailf:info
                "Configure an IPv6 link local address";
              tailf:cli-break-sequence-commands;
            }
            leaf anycast {
              type empty;
              tailf:info
                "Configure an IPv6 anycast address";
              tailf:cli-break-sequence-commands;
            }
          }
          container nat {
            tailf:info
              "Enable NAT on the interface";
            leaf inside {
              tailf:info
                "Configure interface as inside";
              tailf:cli-full-command;
              type empty;
            }
            leaf outside {
              tailf:info
                "Configure interface as outside";
              tailf:cli-full-command;
              type empty;
            }
          }
          container ndisc {
            tailf:info
              "Configure Neighbor Discovery parameters";
            container router-advertisement {
              tailf:info
                "Configure Router Advertisement parameters";
            }
          }
          container ospf;
          container router {
            tailf:info
              "Router";
            container isis {
              tailf:info
                "IS-IS Routing for IP";
              presence "true";
              tailf:cli-reset-container;
              leaf cmds {
                tailf:cli-drop-node-name;
                type string {
                  length "1..255";
                  tailf:info
                    "WORD<length:1-255>;;Specify interface route cmds";
                }
              }
            }
          }
        }
        container ospf;
        container isis;
        leaf l3-vlan-fwd-disable {
          tailf:info
            "Disable L3 forwarding between VLANs for incoming packets on this interface";
          tailf:cli-full-command;
          type empty;
        }
        container lacp {
          tailf:info
            "LACP";
          leaf port-priority {
            tailf:cli-full-command;
            type uint16 {
              range "1..65535";
              tailf:info
                "<1-65535>;;LACP port priority";
            }
          }
          leaf timeout {
            tailf:cli-full-command;
            type enumeration {
              enum "long" {
                tailf:info
                  "Set LACP long timeout";
              }
              enum "short" {
                tailf:info
                  "Set LACP short timeout";
              }
            }
          }
          container trunk {
            tailf:cli-sequence-commands {
              tailf:cli-reset-all-siblings;
            }
            tailf:cli-compact-syntax;
            tailf:info
              "LACP trunk commands";
            leaf number {
              tailf:cli-incomplete-command;
              tailf:cli-drop-node-name;
              type uint16 {
                range "1..16";
                tailf:info
                  "<1-16>;;LACP trunk number";
              }
            }
            leaf admin-key {
              tailf:info
                "LACP admin key";
              tailf:cli-break-sequence-commands;
              must "../number" {
                tailf:xpath-root 3;
                tailf:dependency "../number";
              }
              type uint16 {
                range "10000..65535";
                tailf:info
                  "<10000-65535>;;Admin key value";
              }
            }
            leaf mode {
              tailf:info
                "LACP trunk mode";
              must "../number" {
                tailf:xpath-root 3;
                tailf:dependency "../number";
              }
              type enumeration {
                enum "active" {
                  tailf:info
                    "enable initiation of LACP negotiation on a port";
                }
                enum "passive" {
                  tailf:info
                    "disable initiation of LACP negotiation on a port";
                }
              }
            }
            leaf unidirectional-detection {
              tailf:info
                "LACP Uni-directional detection";
              must "../number" {
                tailf:xpath-root 3;
                tailf:dependency "../number";
              }
              type empty;
            }
          }
          container udld-timeout {
            tailf:info
              "LACP unidirectional-detection timer";
            tailf:cli-sequence-commands {
              tailf:cli-reset-all-siblings;
            }
            tailf:cli-compact-syntax;
            leaf timeout-type {
              tailf:cli-drop-node-name;
              type enumeration {
                enum "fast" {
                  tailf:info
                    "in unit of milli-seconds";
                }
                enum "slow" {
                  tailf:info
                    "in unit of seconds";
                }
              }
            }
            leaf milli {
              tailf:cli-drop-node-name;
              when "../timeout-type = 'fast'" {
                tailf:xpath-root 3;
                tailf:dependency "../timeout-type";
              }
              type uint16 {
                range "100..1000";
                tailf:info
                  "<100-1000>;;timeout in unit of milli-seconds";
              }
            }
            leaf secs {
              tailf:cli-drop-node-name;
              when "../timeout-type = 'slow'" {
                tailf:xpath-root 3;
                tailf:dependency "../timeout-type";
              }
              type uint16 {
                range "1..60";
                tailf:info
                  "<1-60>;;timeout in unit of seconds";
              }
            }
          }
        }
        leaf load-interval {
          tailf:cli-full-command;
          tailf:info
            "Configure Load Interval";
          type uint16 {
            range "5..300";
            tailf:info
              "<5-300>  Seconds (5-300, Multiple of 5), default 300";
          }
        }
        leaf mtu {
          tailf:cli-full-command;
          tailf:info
            "Interface mtu";
          type uint16 {
            range "1200..1500";
          }
          default "1500";
        }
        leaf name {
          tailf:cli-full-command;
          tailf:info
            "Name for the interface";
          type string {
            length "1..63";
            tailf:info
              "WORD<length:1-63>;;Name for the interface";
          }
        }
        leaf speed {
          tailf:cli-full-command;
          type enumeration {
            enum "10" {
              tailf:info
                "10 Mbs/sec";
            }
            enum "100" {
              tailf:info
                "100 Mbs/sec";
            }
            enum "1000" {
              tailf:info
                "1 Gb/sec";
            }
            enum "auto" {
              tailf:info
                "Auto Negotiate Speed";
            }
          }
          default "auto";
        }
      }
      list ve {
        key "id";
        leaf id {
          type leafref {
            path "../../../vlan/router-interface/ve";
          }
        }
        container access-list {
          tailf:info
            "Apply ACL rules to incoming packets on this interface";
          tailf:cli-sequence-commands {
            tailf:cli-reset-siblings;
          }
          tailf:cli-compact-syntax;
          leaf id {
            tailf:cli-drop-node-name;
            tailf:cli-incomplete-command;
            type uint16 {
              range "1..199";
              tailf:info
                "<1-199>;;ACL id";
            }
          }
          leaf in {
            must "../id" {
              tailf:xpath-root 3;
              tailf:dependency "../id";
            }
            type empty;
            tailf:info
              "ACL applied on incoming packets to this interface";
          }
        }
        leaf enabled-disabled {
          tailf:cli-drop-node-name;
          tailf:cli-full-command;
          type enumeration {
            enum "enable" {
              tailf:info
                "Disable Interface";
            }
            enum "disable" {
              tailf:info
                "Enable Interface";
            }
          }
          default "enable";
        }
        container icmp-rate-limit {
          tailf:cli-sequence-commands {
            tailf:cli-reset-siblings;
          }
          tailf:cli-compact-syntax;
          tailf:info
            "Limit ICMP traffic to this interface";
          leaf rate {
            tailf:cli-drop-node-name;
            type uint16 {
              range "1..65535";
              tailf:info
                "<1-65535>;;Normal rate limit. If exceeds this limit, drop the ICMP packet that goes over the limit";
            }
          }
          leaf lockup {
            must "../rate" {
              tailf:xpath-root 3;
              tailf:dependency "../rate";
            }
            tailf:info
              "Enter lockup state when ICMP rate exceeds lockup rate limit";
            type uint16 {
              range "1..65535";
              tailf:info
                "<1-65535>;;Maximum rate limit. If exceeds this limit, drop all ICMP packet for a time period";
            }
            tailf:cli-incomplete-command;
          }
          leaf lockup-perio {
            tailf:cli-drop-node-name;
            must "../lockup" {
              tailf:xpath-root 3;
              tailf:dependency "../lockup";
            }
            type uint16 {
              range "1..65535";
              tailf:info
                "Lockup period (second)";
            }
          }
        }
        container ip {
          tailf:info
            "Global IP configuration subcommands";
          list address {
            key "ip";
            tailf:cli-suppress-mode;
            tailf:info
              "Set the IP address of an interface";
            tailf:cli-sequence-commands {
              tailf:cli-reset-siblings;
            }
            tailf:cli-compact-syntax;
            leaf ip {
              tailf:cli-drop-node-name;
              tailf:cli-incomplete-command;
              type inet:ipv4-address;
            }
            leaf mask {
              tailf:cli-drop-node-name;
              type inet:ipv4-address;
            }
          }
          leaf allow-promiscuous-vip {
            tailf:info
              "Allow traffic to be associated with promiscuous VIP";
            tailf:cli-full-command;
            type empty;
          }
          leaf cache-spoofing-port {
            tailf:info
              "This interface connects to spoofing cache";
            tailf:cli-full-command;
            type empty;
          }
          leaf helper-address {
            tailf:info
              "Helper address for DHCP packets";
            tailf:cli-full-command;
            type inet:ipv4-address;
          }
          container nat {
            tailf:info
              "Enable NAT on the interface";
            leaf inside {
              tailf:info
                "Configure interface as inside";
              tailf:cli-full-command;
              type empty;
            }
            leaf outside {
              tailf:info
                "Configure interface as outside";
              tailf:cli-full-command;
              type empty;
            }
          }
          container ospf;
          container router {
            tailf:info
              "Router";
            container isis {
              tailf:info
                "IS-IS Routing for IP";
              presence "true";
              tailf:cli-reset-container;
              leaf cmds {
                tailf:cli-drop-node-name;
                type string {
                  length "1..255";
                  tailf:info
                    "WORD<length:1-255>;;Specify interface route cmds";
                }
              }
            }
          }
          container tcp {
            tailf:info
              "TCP parameters";
            leaf syn-cookie {
              tailf:info
                "Enable TCP syn-cookie";
              type empty;
            }
          }
        }
        container ipv6 {
          tailf:info
            "Global IP configuration subcommands";
          container access-list {
            tailf:info
              "Apply ACL rules to incoming packets on this interface";
            tailf:cli-sequence-commands {
              tailf:cli-reset-siblings;
            }
            tailf:cli-compact-syntax;
            leaf id {
              tailf:cli-drop-node-name;
              tailf:cli-incomplete-command;
              type string {
                length "1..16";
                tailf:info
                  "WORD<length:1-16>;;Named Access List";
              }
            }
            leaf in {
              must "../id" {
                tailf:xpath-root 3;
                tailf:dependency "../id";
              }
              type empty;
              tailf:info
                "ACL applied on incoming packets to this interface";
            }
          }
          list address {
            key "ip";
            tailf:cli-suppress-mode;
            tailf:info
              "Set the IP address of an interface";
            tailf:cli-sequence-commands {
              tailf:cli-reset-all-siblings;
            }
            tailf:cli-compact-syntax;
            leaf ip {
              tailf:cli-drop-node-name;
              type inet:ipv6-prefix;
            }
            leaf link-local {
              type empty;
              tailf:info
                "Configure an IPv6 link local address";
              tailf:cli-break-sequence-commands;
            }
            leaf anycast {
              type empty;
              tailf:info
                "Configure an IPv6 anycast address";
              tailf:cli-break-sequence-commands;
            }
          }
          container nat {
            tailf:info
              "Enable NAT on the interface";
            leaf inside {
              tailf:info
                "Configure interface as inside";
              tailf:cli-full-command;
              type empty;
            }
            leaf outside {
              tailf:info
                "Configure interface as outside";
              tailf:cli-full-command;
              type empty;
            }
          }
          container ndisc {
            tailf:info
              "Configure Neighbor Discovery parameters";
            container router-advertisement {
              tailf:info
                "Configure Router Advertisement parameters";
            }
          }
          container ospf;
          container router {
            tailf:info
              "Router";
            container isis {
              tailf:info
                "IS-IS Routing for IP";
              presence "true";
              tailf:cli-reset-container;
              leaf cmds {
                tailf:cli-drop-node-name;
                type string {
                  length "1..255";
                  tailf:info
                    "WORD<length:1-255>;;Specify interface route cmds";
                }
              }
            }
          }
        }
        container isis;
        leaf l3-vlan-fwd-disable {
          tailf:info
            "Disable L3 forwarding between VLANs for incoming packets on this interface";
          tailf:cli-full-command;
          type empty;
        }
        leaf name {
          tailf:cli-full-command;
          tailf:info
            "Name for the interface";
          type string {
            length "1..63";
            tailf:info
              "WORD<length:1-63>;;Name for the interface";
          }
        }
        container ospf;
      }
    }
    container ip {
      tailf:ncs-device-type "cli-ned";
      tailf:display-when "not(../../ncs:module) or ../../ncs:module[ncs:name='tailf-ned-a10-acos']";
      tailf:info
        "Global IP configuration subcommands";
      list address {
        key "ip";
        tailf:cli-suppress-mode;
        tailf:info
          "Set the IP address of an interface";
        tailf:cli-sequence-commands {
          tailf:cli-reset-siblings;
        }
        tailf:cli-compact-syntax;
        leaf ip {
          tailf:cli-drop-node-name;
          tailf:cli-incomplete-command;
          type inet:ipv4-address;
        }
        leaf mask {
          tailf:cli-drop-node-name;
          type inet:ipv4-address;
        }
      }
      container anomaly-drop {
        tailf:info
          "set IP anomaly drop policy";
        leaf bad-content {
          tailf:cli-full-command;
          tailf:info
            "bad content threshold";
          type uint16 {
            range "1..127";
            tailf:info
              "<1-127>;;threshold value";
          }
        }
        leaf drop-all {
          tailf:info
            "drop all IP anomaly packets";
          tailf:cli-full-command;
          type empty;
        }
        leaf frag {
          tailf:info
            "drop all fragmented";
          tailf:cli-full-command;
          type empty;
        }
        leaf ip-option {
          tailf:info
            "drop packets with IP options";
          tailf:cli-full-command;
          type empty;
        }
        leaf land-attack {
          tailf:info
            "drop IP packets with the same source and destination addresses";
          tailf:cli-full-command;
          type empty;
        }
        leaf out-of-sequence {
          tailf:cli-full-command;
          tailf:info
            "out of sequence packet threshold";
          type uint16 {
            range "1..127";
            tailf:info
              "<1-127>;;threshold value";
          }
        }
        leaf ping-of-death {
          tailf:info
            "drop oversize ICMP packets";
          tailf:cli-full-command;
          type empty;
        }
        leaf tcp-no-flag {
          tailf:info
            "drop TCP packets with no flag";
          tailf:cli-full-command;
          type empty;
        }
        leaf tcp-syn-fin {
          tailf:info
            "drop TCP packets with both syn and fin flags set";
          tailf:cli-full-command;
          type empty;
        }
        leaf tcp-syn-frag {
          tailf:info
            "drop fragmented TCP packets with syn flag set";
          tailf:cli-full-command;
          type empty;
        }
        leaf zero-window {
          tailf:info
            "zero window size threshold";
          tailf:cli-full-command;
          type uint16 {
            range "1..127";
            tailf:info
              "<1-127>;;threshold value";
          }
        }
      }
      container as-path {
        tailf:info
          "AS-PATH";
        list access-list {
          tailf:cli-suppress-mode;
          key "name action path";
          leaf name {
            type string {
              tailf:info
                "WORD;;Regular expression access list name";
            }
          }
          leaf action {
            type enumeration {
              enum "permit" {
                tailf:info
                  "Specify packets to forward";
              }
              enum "deny" {
                tailf:info
                  "Specify packets to reject";
              }
            }
          }
          leaf path {
            type string;
            tailf:cli-multi-word-key;
          }
        }
      }
      container community-list {
        tailf:info
          "Community-list";
        list standard-number {
          tailf:cli-drop-node-name;
          tailf:cli-suppress-mode;
          key "nr";
          leaf nr {
            type uint8 {
              range "1..99";
            }
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "AA:NN local-AS no-advertise no-export";
            }
          }
        }
        list expanded-number {
          tailf:cli-drop-node-name;
          tailf:cli-suppress-mode;
          key "nr";
          leaf nr {
            type uint8 {
              range "100..199";
            }
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "LINE";
            }
          }
        }
        list word {
          tailf:cli-drop-node-name;
          tailf:cli-suppress-mode;
          key "name";
          leaf name {
            type string;
            tailf:cli-disallow-value "(expanded)|(standard)";
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "AA:NN local-AS no-advertise no-export";
            }
          }
        }
        list expanded {
          tailf:cli-suppress-mode;
          key "name";
          leaf name {
            type string;
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "LINE";
            }
          }
        }
        list standard {
          tailf:cli-suppress-mode;
          key "name";
          leaf name {
            type string;
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "AA:NN local-AS no-advertise no-export";
            }
          }
        }
      }
      leaf default-gateway {
        tailf:info
          "Transparent mode gateway";
        type inet:ipv4-address;
        tailf:cli-full-command;
      }
      container dns {
        leaf primary {
          type inet:ipv4-address;
          tailf:cli-full-command;
        }
        leaf secondary {
          type inet:ipv4-address;
          tailf:cli-full-command;
        }
        leaf suffix {
          type string;
          tailf:cli-full-command;
        }
      }
      container extcommunity-list {
        tailf:info
          "Community-list";
        list standard-number {
          tailf:cli-drop-node-name;
          tailf:cli-suppress-mode;
          key "nr";
          leaf nr {
            type uint8 {
              range "1..99";
            }
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "LINE;;rt Route Target extended community in aa:nn or IPaddr:nn format OR soo Site-of-Origin extended community in aa:nn or IPaddr:nn format";
            }
          }
        }
        list expanded-number {
          tailf:cli-drop-node-name;
          tailf:cli-suppress-mode;
          key "nr";
          leaf nr {
            type uint8 {
              range "100..199";
            }
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "LINE";
            }
          }
        }
        list expanded {
          tailf:cli-suppress-mode;
          key "name";
          leaf name {
            type string;
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "LINE";
            }
          }
        }
        list standard {
          tailf:cli-suppress-mode;
          key "name";
          leaf name {
            type string;
          }
          list rules {
            tailf:cli-drop-node-name;
            tailf:cli-suppress-mode;
            key "action expr";
            leaf action {
              type enumeration {
                enum "deny" {
                  tailf:info
                    "Specify community to reject";
                }
                enum "permit" {
                  tailf:info
                    "Specify community to accept";
                }
              }
            }
            leaf expr {
              type string;
              tailf:cli-multi-word-key;
              tailf:info
                "LINE;;rt Route Target extended community in aa:nn or IPaddr:nn format OR soo Site-of-Origin extended community in aa:nn or IPaddr:nn format";
            }
          }
        }
      }
      container frag {
        tailf:info
          "IP fragmentation parameters";
        leaf buff {
          tailf:cli-full-command;
          tailf:info
            "max buff used for fragmentation";
          type uint32 {
            range "10000..3000000";
            tailf:info
              "<10000-3000000>";
          }
        }
        leaf max-reassembly-sessions {
          tailf:cli-full-command;
          tailf:info
            "Max number of pending reassembly sessions allowed (default 100000)";
          type uint32 {
            range "1..200000";
            tailf:info
              "<1-200000>;;Max number of pending reassembly sessions allowed (default 100000)";
          }
        }
        leaf timeout {
          tailf:cli-full-command;
          tailf:info
            "fragmentation timeout";
          type uint16 {
            range "4..16000";
            tailf:info
              "<4-16000>;;in milliseconds 4 - 16000 (default is 1000)";
          }
        }
      }
      container icmp {
        tailf:info
          "Global ICMP commands";
        container disable {
          tailf:info
            "Disable";
          leaf redirect {
            tailf:info
              "Disable outbound ICMP redirect messages";
            tailf:cli-full-command;
            type empty;
          }
          leaf unreachable {
            tailf:info
              "Disable outbound ICMP unreachable messages";
            tailf:cli-full-command;
            type empty;
          }
        }
      }

      grouping mgmt-source-interface-grouping {
        container source-interface {
          tailf:info
            "Interface to get source IP";
          leaf loopback {
            tailf:info
              "Loopback interface";
            type uint8 {
              range "1..10";
              tailf:info
                "<1-10>;;Loopback interface number";
            }
          }
        }
      }
      container mgmt-traffic {
        container snmp {
          uses mgmt-source-interface-grouping;
        }
        container ntp {
          uses mgmt-source-interface-grouping;
        }
        container syslog {
          uses mgmt-source-interface-grouping;
        }
        container ssh {
          uses mgmt-source-interface-grouping;
        }
        container telnet {
          uses mgmt-source-interface-grouping;
        }
        container ftp {
          uses mgmt-source-interface-grouping;
        }
        container tftp {
          uses mgmt-source-interface-grouping;
        }
        container rcp {
          uses mgmt-source-interface-grouping;
        }
        container web {
          uses mgmt-source-interface-grouping;
        }
        container all {
          uses mgmt-source-interface-grouping;
        }
      }
      container nat {
        container alg {
          leaf pptp {
            type enumeration {
              enum "disable";
              enum "enable";
            }
            default "enable";
          }
        }
        leaf allow-static-host {
          tailf:info
            "Enable Static IP Address Support";
          tailf:cli-full-command;
          type empty;
        }
        container inside {
          container source;
        }
        list pool {
          tailf:cli-remove-before-change;
          tailf:cli-suppress-mode;
          tailf:cli-sequence-commands {
            tailf:cli-reset-all-siblings;
          }
          tailf:cli-compact-syntax;
          tailf:cli-incomplete-command;
          key "name";
          leaf name {
            type string {
              length "1..31";
              tailf:info
                "WORD<length:1-31>  Pool Name or Pool Group";
            }
          }
          leaf ipstart {
            mandatory true;
            tailf:cli-incomplete-command;
            tailf:cli-drop-node-name;
            type inet:ipv4-address {
              tailf:info
                "A.B.C.D;;Start IP Address of NAT pool";
            }
          }
          leaf ipend {
            mandatory true;
            tailf:cli-incomplete-command;
            tailf:cli-drop-node-name;
            type inet:ipv4-address {
              tailf:info
                "A.B.C.D;;End IP Address of NAT pool";
            }
          }
          leaf netmask {
            mandatory true;
            tailf:info
              "Configure Mask for Pool";
            type string {
              tailf:info
                "/nn;;Configure Mask for Pool";
            }
          }
          leaf gateway {
            tailf:info
              "Gateway IP";
            tailf:cli-optional-in-sequence;
            type inet:ipv4-address {
              tailf:info
                "A.B.C.D;;Gateway IP";
            }
          }
          leaf ha-group-id {
            tailf:info
              "HA Group ID";
            tailf:cli-optional-in-sequence;
            type uint16 {
              range "1..31";
              tailf:info
                "<1-31>;;HA Group ID 1 to 31";
            }
          }
          leaf ha-use-all-ports {
            tailf:info
              "Specify this if services using this NAT pool are transaction based (immediate aging)";
            tailf:cli-optional-in-sequence;
            type empty;
            when "../ha-group-id" {
              tailf:xpath-root 3;
              tailf:dependency "../ha-group-id";
            }
          }
          leaf vrid {
            tailf:info
              "VRRP vrid";
            tailf:cli-optional-in-sequence;
            when "not(../ha-group-id)" {
              tailf:xpath-root 3;
              tailf:dependency "../ha-group-id";
            }
            type uint16 {
              range "1..31";
              tailf:info
                "<1-31>;;VRRP vrid 1 to 31";
            }
          }
          leaf ip-rr {
            tailf:info
              "Use IP address round-robin behavior";
            type empty;
          }
        }
        container pool-group;
        container range-list;
        leaf reset-idle-tcp-conn {
          tailf:cli-full-command;
          tailf:info
            "Reset Idle TCP Connections";
          type empty;
        }
        container template {
          list logging {
            key "name";
            leaf name {
              tailf:cli-full-command;
              type string {
                length "1..63";
              }
            }
          }
        }
        container translation;
      }
      container prefix-list;
      list route {
        key "ip mask";
        tailf:cli-sequence-commands;
        tailf:cli-compact-syntax;
        tailf:cli-incomplete-command;
        tailf:cli-suppress-mode;
        leaf ip {
          type inet:ipv4-address;
          tailf:info
            "A.B.C.D;;Destination prefix";
        }
        leaf mask {
          type union {
            type string {
              tailf:info
                "/nn";
              pattern '/[0-9][0-9]?';
            }
            type inet:ipv4-address {
              tailf:info
                "A.B.C.D;;Destination prefix mask";
            }
          }
        }
        leaf forwarding-router {
          tailf:cli-drop-node-name;
          type inet:ipv4-address {
            tailf:info
              "A.B.C.D;;Forwarding router's address";
          }
        }
        leaf distance {
          must "../forwarding-router" {
            tailf:xpath-root 3;
            tailf:dependency "../forwarding-router";
          }
          tailf:cli-drop-node-name;
          type uint8 {
            range "1..255";
            tailf:info
              "<1-255>;;Distance value for this route";
          }
        }
      }
      container tcp {
        tailf:info
          "Global TCP parameters";
        container syn-cookie {
          tailf:info
            "SYN cookie parameters";
          leaf threshold {
            tailf:info
              "SYN cookie expire threshold";
            type uint8 {
              range "1..100";
              tailf:info
                "<1-100>;;seconds (default is 4)";
            }
          }
        }
      }
    }
    container floating-ip {
      tailf:ncs-device-type "cli-ned";
      tailf:display-when "not(../../ncs:module) or ../../ncs:module[ncs:name='tailf-ned-a10-acos']";
      tailf:info
        "Floating IP Configuration";
      list ipv4 {
        tailf:cli-remove-before-change;
        tailf:cli-suppress-mode;
        tailf:cli-drop-node-name;
        tailf:cli-compact-syntax;
        key "ip";
        leaf ip {
          type inet:ipv4-address {
            tailf:info
              "A.B.C.D;;IP Address";
          }
        }
        leaf ha-group {
          tailf:info
            "Join a Failover Group";
          type leafref {
            path "../../../ha/group/id";
          }
        }
      }
      list ipv6 {
        tailf:cli-drop-node-name;
        tailf:cli-suppress-mode;
        tailf:cli-remove-before-change;
        tailf:cli-compact-syntax;
        key "ip";
        leaf ip {
          type inet:ipv6-address {
            tailf:info
              "A:B:C:D:E:F:G:H;;IPV6 address";
          }
        }
        leaf anycast {
          tailf:info
            "Configure an IPv6 anycast address";
          tailf:cli-incomplete-command;
          type empty;
        }
        leaf ha-group {
          tailf:info
            "Join a Failover Group";
          tailf:cli-full-command;
          type leafref {
            path "../../../ha/group/id";
          }
        }
      }
    }
    container health {
      tailf:ncs-device-type "cli-ned";
      tailf:display-when "not(../../ncs:module) or ../../ncs:module[ncs:name='tailf-ned-a10-acos']";
      tailf:info
        "Configure health monitoring";
      list monitor {
        tailf:info
          "Define the Health Monitor object";
        key "name";
        leaf name {
          type string {
            length "1..29";
            tailf:info
              "WORD<length:1-29>;;Monitor Name";
          }
        }
        leaf interval {
          tailf:info
            "Specify the Healthcheck Interval";
          tailf:cli-hide-in-submode;
          type uint8 {
            range "1..180";
            tailf:info
              " <1-180>;;Interval Value, in seconds (default 5)";
          }
        }
        leaf retry {
          tailf:info
            "Specify the Healthcheck Retries";
          tailf:cli-hide-in-submode;
          type uint8 {
            range "1..5";
            tailf:info
              "<1-5>;;Retry Count (default 3)";
          }
          default "3";
        }
        leaf timeout {
          tailf:info
            "Specify the Healthcheck Timeout";
          tailf:cli-hide-in-submode;
          type uint8 {
            range "1..12";
            tailf:info
              "<1-12>  Timeout Value, in seconds (default 5)";
          }
          default "5";
        }
        leaf up-retry {
          tailf:info
            "Specify the Healthcheck Retries before declaring target up";
          tailf:cli-hide-in-submode;
          type uint8 {
            range "1..10";
            tailf:info
              "<1-10>;;Up-retry count (default 1)";
          }
          default "1";
        }
        leaf strictly-retry-on-server-error-response {
          tailf:info
            "Require strictly retry";
          tailf:cli-full-command;
          type empty;
        }
        leaf disable-after-down {
          tailf:info
            "Disable the target if health check failed";
          tailf:cli-full-command;
          type empty;
        }
        leaf override-port {
          tailf:info
            "Override implicitly inherited port from target";
          tailf:cli-full-command;
          type uint16 {
            range "1..65535";
            tailf:info
              "<1-65534>;;Port number (1-65534)";
          }
        }
        leaf override-ipv4 {
          tailf:info
            "Override implicitly inherited IPv4 address from target";
          tailf:cli-full-command;
          type inet:ipv4-address {
            tailf:info
              "A.B.C.D;;IPv4 address";
          }
        }
        leaf override-ipv6 {
          tailf:info
            "Override implicitly inherited IPv4 address from target";
          tailf:cli-full-command;
          type inet:ipv6-address {
            tailf:info
              "A:B:C:D:E:F:G:H;;IPv6 address";
          }
        }
        container method {
          tailf:info
            "Define the health method object, default is icmp";
          choice method-choice {
            container icmp {
              tailf:info
                "ICMP type";
              presence "true";
              leaf transparent {
                tailf:cli-reset-container;
                tailf:info
                  "Apply Transparent Mode";
                type union {
                  type inet:ipv4-address {
                    tailf:info
                      "A.B.C.D;;IPv4 address of destination behind monitored node";
                  }
                  type inet:ipv6-address {
                    tailf:info
                      "A:B:C:D:E:F:G:H;;IPv6 address of destination behind monitored node";
                  }
                }
              }
            }
            container http {
              tailf:info
                "HTTP type";
              tailf:cli-compact-syntax;
              presence "true";
              leaf port {
                tailf:info
                  "Specify HTTP Port";
                tailf:cli-reset-container;
                type uint16 {
                  range "1..65534";
                  tailf:info
                    "<1-65534>;;Port Number (default 80)";
                }
                default "80";
              }
              container username {
                tailf:cli-flatten-container;
                tailf:cli-reset-container;
                tailf:cli-compact-syntax;
                tailf:cli-sequence-commands {
                  tailf:cli-reset-siblings;
                }
                tailf:info
                  "Specify the username";
                leaf name {
                  tailf:cli-drop-node-name;
                  tailf:cli-incomplete-command;
                  type string {
                    length "1..31";
                    tailf:info
                      "WORD<length:1-31>;;Username";
                  }
                }
                leaf password {
                  must "../name" {
                    tailf:xpath-root 3;
                    tailf:dependency "../name";
                  }
                  tailf:cli-incomplete-command;
                  type empty;
                }
                leaf cleartext {
                  tailf:cli-drop-node-name;
                  tailf:cli-disallow-value "encrypted";
                  tailf:cli-optional-in-sequence;
                  type string {
                    tailf:info
                      "WORD<length:0-31>  Password, '' means empty password";
                    length "0..31";
                  }
                }
                leaf encrypted {
                  when "../password and not(../cleartext)" {
                    tailf:xpath-root 3;
                    tailf:dependency "../password";
                    tailf:dependency "../cleartext";
                  }
                  tailf:info
                    "Specify the user password";
                  type string;
                }
              }
              container url {
                tailf:cli-flatten-container;
                tailf:cli-compact-syntax;
                tailf:cli-reset-container;
                tailf:cli-sequence-commands {
                  tailf:cli-reset-siblings;
                }
                leaf method {
                  tailf:cli-drop-node-name;
                  tailf:cli-incomplete-command;
                  type enumeration {
                    enum "GET" {
                      tailf:info
                        "HTTP GET Method";
                    }
                    enum "POST" {
                      tailf:info
                        "HTTP POST Method";
                    }
                  }
                }
                leaf path {
                  must "../method" {
                    tailf:xpath-root 3;
                    tailf:dependency "../method";
                  }
                  tailf:cli-drop-node-name;
                  type string {
                    length "1..127";
                    tailf:info
                      "WORD<length:1-127>  Specifies URL Path, the default is '/'";
                  }
                }
              }
              container expect {
                tailf:info
                  "Specify what you expect from the response message";
                tailf:cli-flatten-container;
                tailf:cli-reset-container;
                tailf:cli-compact-syntax;
                choice expect-choice {
                  leaf response-code {
                    tailf:info
                      "response code range (e.g. 200, 400-430)";
                    type string {
                      length "1..31";
                      tailf:info
                        "WORD<length:1-31>;;format is xx,xx-xx (xx between [100, 899])";
                    }
                  }
                  leaf text {
                    tailf:cli-drop-node-name;
                    type string {
                      length "1..127";
                      tailf:info
                        "WORD<length:1-127>;;Text Expected";
                    }
                    tailf:cli-disallow-value "response-code";
                  }
                }
              }
              leaf maintenance-code {
                tailf:info
                  "Specify response code for maintenance";
                type string {
                  length "1..31";
                  tailf:info
                    "WORD<length:1-31>;;format is xx,xx-xx (xx between [100, 899])";
                }
              }
              leaf host {
                tailf:info
                  "Specify 'Host:' header used in request (enclose IPv6 address in [])";
                type string {
                  length "1..63";
                  tailf:info
                    "WORD<length:1-63>;;Host";
                }
              }
            }
            container https {
              tailf:info
                "HTTPS type";
              tailf:cli-compact-syntax;
              presence "true";
              leaf port {
                tailf:info
                  "Specify HTTP Port";
                tailf:cli-reset-container;
                type uint16 {
                  range "1..65534";
                  tailf:info
                    "<1-65534>;;Port Number (default 80)";
                }
                default "80";
              }
              leaf disable-sslv2hello {
                tailf:cli-reset-container;
                tailf:info
                  "Disable SSLv2Hello for HTTPS";
                type empty;
              }
              container username {
                tailf:cli-flatten-container;
                tailf:cli-reset-container;
                tailf:cli-compact-syntax;
                tailf:cli-sequence-commands {
                  tailf:cli-reset-siblings;
                }
                tailf:info
                  "Specify the username";
                leaf name {
                  tailf:cli-drop-node-name;
                  tailf:cli-incomplete-command;
                  type string {
                    length "1..31";
                    tailf:info
                      "WORD<length:1-31>;;Username";
                  }
                }
                leaf password {
                  must "../name" {
                    tailf:xpath-root 3;
                    tailf:dependency "../name";
                  }
                  tailf:cli-incomplete-command;
                  type empty;
                }
                leaf cleartext {
                  tailf:cli-drop-node-name;
                  tailf:cli-disallow-value "encrypted";
                  tailf:cli-optional-in-sequence;
                  type string {
                    tailf:info
                      "WORD<length:0-31>  Password, '' means empty password";
                    length "0..31";
                  }
                }
                leaf encrypted {
                  when "../password and not(../cleartext)" {
                    tailf:xpath-root 3;
                    tailf:dependency "../password";
                    tailf:dependency "../cleartext";
                  }
                  tailf:info
                    "Specify the user password";
                  type string;
                }
              }
              container url {
                tailf:cli-flatten-container;
                tailf:cli-reset-container;
                tailf:cli-compact-syntax;
                tailf:cli-sequence-commands {
                  tailf:cli-reset-siblings;
                }
                leaf method {
                  tailf:cli-drop-node-name;
                  tailf:cli-incomplete-command;
                  type enumeration {
                    enum "GET" {
                      tailf:info
                        "HTTP GET Method";
                    }
                    enum "POST" {
                      tailf:info
                        "HTTP POST Method";
                    }
                  }
                }
                leaf path {
                  must "../method" {
                    tailf:xpath-root 3;
                    tailf:dependency "../method";
                  }
                  tailf:cli-drop-node-name;
                  type string {
                    length "1..127";
                    tailf:info
                      "WORD<length:1-127>  Specifies URL Path, the default is '/'";
                  }
                }
              }
              container expect {
                tailf:info
                  "Specify what you expect from the response message";
                tailf:cli-flatten-container;
                tailf:cli-compact-syntax;
                choice expect-choice {
                  leaf response-code {
                    tailf:info
                      "response code range (e.g. 200, 400-430)";
                    type string {
                      length "1..31";
                      tailf:info
                        "WORD<length:1-31>;;format is xx,xx-xx (xx between [100, 899])";
                    }
                  }
                  leaf text {
                    tailf:cli-drop-node-name;
                    type string {
                      length "1..127";
                      tailf:info
                        "WORD<length:1-127>;;Text Expected";
                    }
                    tailf:cli-disallow-value "response-code";
                  }
                }
              }
              leaf maintenance-code {
                tailf:info
                  "Specify response code for maintenance";
                type string {
                  length "1..31";
                  tailf:info
                    "WORD<length:1-31>;;format is xx,xx-xx (xx between [100, 899])";
                }
              }
              leaf host {
                tailf:info
                  "Specify 'Host:' header used in request (enclose IPv6 address in [])";
                type string {
                  length "1..63";
                  tailf:info
                    "WORD<length:1-63>;;Host";
                }
              }
            }
            container tcp {
              tailf:info
                "TCP type";
              tailf:cli-compact-syntax;
              leaf port {
                tailf:info
                  "Specify TCP Port";
                tailf:cli-reset-container;
                type uint16 {
                  range "1..65534";
                  tailf:info
                    "<1-65534>;;Port Number";
                }
              }
              leaf halfopen {
                tailf:cli-reset-container;
                tailf:info
                  "TCP SYN Check";
                type empty;
              }
            }
            container udp {
              tailf:info
                "UDP type";
              leaf port {
                tailf:info
                  "Specify UDP Port";
                type uint16 {
                  range "1..65534";
                  tailf:info
                    "<1-65534>;;Port Number";
                }
              }
            }
            container ftp {
              tailf:info
                "FTP type";
              tailf:cli-compact-syntax;
              leaf port {
                tailf:info
                  "Specify FTP Port";
                tailf:cli-reset-container;
                type uint16 {
                  range "1..65534";
                  tailf:info
                    "<1-65534>;;Port Number (default 21)";
                }
                default "21";
              }
              container credentials {
                tailf:info
                  "FTP credentials";
                tailf:cli-flatten-container;
                tailf:cli-reset-container;
                tailf:cli-sequence-commands {
                  tailf:cli-reset-siblings;
                }
                tailf:cli-compact-syntax;
                tailf:cli-drop-node-name;
                presence "FTP credentials";
                leaf username {
                  tailf:info
                    "Specify the username";
                  tailf:cli-incomplete-command;
                  type string {
                    length "1..31";
                    tailf:info
                      "WORD<length:1-31>;;Username";
                  }
                }
                container password {
                  tailf:info
                    "Specify the user password";
                  tailf:cli-flatten-container;
                  tailf:cli-compact-syntax;
                  choice ftp-pass-choice {
                    leaf cleartext {
                      tailf:cli-drop-node-name;
                      tailf:cli-disallow-value "encrypted";
                      type string {
                        length "0..31";
                        tailf:info
                          "WORD<length:0-31>;;Password, '' means empty password";
                      }
                    }
                    leaf encrypted {
                      tailf:info
                        "Do NOT use this option manually. (This is an A10 reserved keyword.)";
                      type string {
                        length "1..255";
                        tailf:info
                          "WORD<length:1-255>;;The ENCRYPTED password string";
                      }
                    }
                  }
                }
              }
            }
            container snmp {
              tailf:info
                "SNMP type";
              tailf:cli-compact-syntax;
              leaf community {
                tailf:cli-reset-container;
                tailf:info
                  "Specify SNMP Community, by default 'public'";
                type string {
                  length "1..31";
                  tailf:info
                    "WORD<length:1-31>;;Community String";
                }
              }
              leaf oid {
                tailf:info
                  "Specify MIB-2 OID, by default sysDescr (MIB-2 oid 1.3.6.1.2.1 prepended)";
                tailf:cli-reset-container;
                type union {
                  type enumeration {
                    enum "sysDescr" {
                      tailf:info
                        "The MIB-2 OID of System Description, 1.1.0";
                    }
                    enum "sysUpTime" {
                      tailf:info
                        "The MIB-2 OID of System Up Time, 1.3.0";
                    }
                    enum "sysName" {
                      tailf:info
                        "The MIB-2 OID of System Name, 1.5.0";
                    }
                  }
                  type string {
                    length "1..128";
                    tailf:info
                      "WORD<length:1-128>;;The format in ASN.1 style";
                  }
                }
              }
              leaf operation {
                tailf:info
                  "Specify SNMP command, by default get";
                tailf:cli-reset-container;
                type enumeration {
                  enum "get" {
                    tailf:info
                      "Get-Request command";
                  }
                  enum "getnext" {
                    tailf:info
                      "Get-Next-Request command";
                  }
                }
              }
              leaf port {
                tailf:info
                  "Specify SNMP Port, by default 161";
                tailf:cli-reset-container;
                type uint16 {
                  range "1..65534";
                  tailf:info
                    "<1-65534>;;Port Number";
                }
                default "161";
              }
            }
            container smtp {
              tailf:info
                "SMTP type";
              tailf:cli-compact-syntax;
              leaf domain {
                tailf:cli-reset-container;
                tailf:info
                  "Specify domain name of 'helo' command";
                type string {
                  length "1..255";
                  tailf:info
                    "Domain name;;Domain Name <1-255>";
                }
              }
              leaf port {
                tailf:info
                  "Specify SMTP Port";
                tailf:cli-reset-container;
                type uint16 {
                  range "1..65534";
                  tailf:info
                    "<1-65534>;;Port Number (default 25)";
                }
                default "25";
              }
            }
            container dns {
              tailf:info
                "DNS type";
              tailf:cli-compact-syntax;
              tailf:cli-sequence-commands {
                tailf:cli-reset-all-siblings;
              }
              choice dns-health-choice {
                leaf domain {
                  tailf:info
                    "Specify Fully Qualified Domain Name of the host";
                  type string {
                    length "1..255";
                    tailf:info
                      "Domain name;;Domain Name <1-255>";
                  }
                }
                leaf ipaddress {
                  tailf:info
                    "Reverse DNS lookup";
                  type inet:ip-address {
                    tailf:info
                      "WORD<length:1-63>;;ipv4 or ipv6 address";
                  }
                }
              }
              container expect {
                tailf:cli-flatten-container;
                tailf:cli-compact-syntax;
                tailf:cli-break-sequence-commands;
                leaf response-code {
                  type string {
                    length "1..31";
                    tailf:info
                      "WORD<length:1-31>;;format is xx,xx-xx(xx between[0, 15])";
                  }
                }
              }
              leaf port {
                tailf:info
                  "Specify DNS Port (default 53)";
                type uint16 {
                  range "1..65534";
                  tailf:info
                    "<1-65534>;;DNS Port(default 53)";
                }
                default "53";
              }
              leaf recurse {
                tailf:info
                  "enable recursion bit or not(default enabled)";
                type enumeration {
                  enum "enabled" {
                    tailf:info
                      "set the recursion bit";
                  }
                  enum "disabled" {
                    tailf:info
                      "clear the recursion bit";
                  }
                }
              }
              leaf type {
                tailf:info
                  "query type(default A)";
                when "../domain" {
                  tailf:xpath-root 3;
                }
                type enumeration {
                  enum "A" {
                    tailf:info
                      "Used for storing Ipv4 address(default)";
                  }
                  enum "CNAME" {
                    tailf:info
                      "Canonical name for a DNS alias";
                  }
                  enum "SOA" {
                    tailf:info
                      "Start of authority";
                  }
                  enum "PTR" {
                    tailf:info
                      "Domain name pointer";
                  }
                  enum "MX" {
                    tailf:info
                      "Mail exchanger";
                  }
                  enum "TXT" {
                    tailf:info
                      "Text string";
                  }
                  enum "AAAA" {
                    tailf:info
                      "Used for storing Ipv6 128-bits address";
                  }
                }
              }
            }
            container pop3 {
              tailf:info
                "POP3 type";
              tailf:cli-compact-syntax;
              leaf port {
                tailf:info
                  "Specify the POP3 port";
                tailf:cli-reset-container;
                type uint16 {
                  range "1..65534";
                  tailf:info
                    "<1-65534>;;Port Number (default 110)";
                }
                default "110";
              }
              container credentials {
                tailf:info
                  "POP3 credentials";
                tailf:cli-flatten-container;
                tailf:cli-reset-container;
                tailf:cli-sequence-commands {
                  tailf:cli-reset-siblings;
                }
                tailf:cli-compact-syntax;
                tailf:cli-drop-node-name;
                presence "POP3 credentials";
                leaf username {
                  tailf:info
                    "Specify the username";
                  tailf:cli-incomplete-command;
                  type string {
                    length "1..31";
                    tailf:info
                      "WORD<length:1-31>;;Username";
                  }
                }
                container password {
                  tailf:info
                    "Specify the user password";
                  tailf:cli-flatten-container;
                  tailf:cli-compact-syntax;
                  choice ftp-pass-choice {
                    leaf cleartext {
                      tailf:cli-drop-node-name;
                      tailf:cli-disallow-value "encrypted";
                      type string {
                        length "0..31";
                        tailf:info
                          "WORD<length:0-31>;;Password, '' means empty password";
                      }
                    }
                    leaf encrypted {
                      tailf:info
                        "Do NOT use this option manually. (This is an A10 reserved keyword.)";
                      type string {
                        length "1..255";
                        tailf:info
                          "WORD<length:1-255>;;The ENCRYPTED password string";
                      }
                    }
                  }
                }
              }
            }
            container imap {
              tailf:info
                "IMAP type";
              tailf:cli-compact-syntax;
              leaf port {
                tailf:info
                  "Specify the IMAP port";
                tailf:cli-reset-container;
                type uint16 {
                  range "1..65534";
                  tailf:info
                    "<1-65534>;;Port Number (default 110)";
                }
                default "110";
              }
              container credentials {
                tailf:info
                  "IMAP credentials";
                tailf:cli-flatten-container;
                tailf:cli-reset-container;
                tailf:cli-sequence-commands {
                  tailf:cli-reset-all-siblings;
                }
                tailf:cli-compact-syntax;
                tailf:cli-drop-node-name;
                presence "IMAP credentials";
                leaf username {
                  tailf:info
                    "Specify the username";
                  tailf:cli-incomplete-command;
                  type string {
                    length "1..31";
                    tailf:info
                      "WORD<length:1-31>;;Username";
                  }
                }
                container password {
                  tailf:info
                    "Specify the user password";
                  tailf:cli-flatten-container;
                  tailf:cli-compact-syntax;
                  choice ftp-pass-choice {
                    leaf cleartext {
                      tailf:cli-drop-node-name;
                      tailf:cli-disallow-value "encrypted";
                      type string {
                        length "0..31";
                        tailf:info
                          "WORD<length:0-31>;;Password, '' means empty password";
                      }
                    }
                    leaf encrypted {
                      tailf:info
                        "Do NOT use this option manually. (This is an A10 reserved keyword.)";
                      type string {
                        length "1..255";
                        tailf:info
                          "WORD<length:1-255>;;The ENCRYPTED password string";
                      }
                    }
                  }
                }
              }
              leaf-list auth {
                when "../credentials and ../credentials/username and (../credentials/password/cleartext or  ../credentials/password/encrypted)" {
                  tailf:xpath-root 3;
                  tailf:dependency "../credentials";
                  tailf:dependency "../credentials/username";
                  tailf:dependency "../credentials/password/cleartext";
                  tailf:dependency "../credentials/password/encrypted";
                }
                tailf:info
                  "Specify the Authentication method";
                tailf:cli-flat-list-syntax;
                type enumeration {
                  enum "plain" {
                    tailf:info
                      "Plain Text";
                  }
                  enum "cram-md5" {
                    tailf:info
                      "Challenge-Response Authentication Mechanism";
                  }
                  enum "login" {
                    tailf:info
                      "Simple Login";
                  }
                }
              }
            }
            container sip {
              tailf:info
                "SIP type";
              tailf:cli-compact-syntax;
              leaf port {
                tailf:info
                  "Specify the SIP port.(Default: 5060)";
                tailf:cli-reset-container;
                type uint16 {
                  range "1..65534";
                  tailf:info
                    "<1-65534>;;Port Number";
                }
                default "5060";
              }
              leaf register {
                tailf:info
                  "Send SIP REGISTER message. (Default: send OPTION message)";
                tailf:cli-reset-container;
                type empty;
              }
              leaf tcp {
                tailf:info
                  "TCP will be used for transmission (Default: UDP)";
                tailf:cli-reset-container;
                type empty;
              }
            }
            container radius {
              tailf:info
                "RADIUS type";
              tailf:cli-compact-syntax;
              leaf port {
                tailf:info
                  "Specify the RADIUS port";
                tailf:cli-reset-container;
                type uint16 {
                  range "1..65534";
                  tailf:info
                    "<1-65534>;;Port number (default 1812)";
                }
                default "1812";
              }
              leaf secret {
                tailf:info
                  "Specify the Shared Secret of RADIUS server";
                tailf:cli-reset-container;
                type string {
                  length "1..31";
                  tailf:info
                    "WORD<length:1-31>;;Shared Crypto Key";
                }
              }
              container credentials {
                tailf:info
                  "RADIUS credentials";
                tailf:cli-flatten-container;
                tailf:cli-sequence-commands {
                  tailf:cli-reset-siblings;
                }
                tailf:cli-compact-syntax;
                tailf:cli-drop-node-name;
                presence "RADIUS credentials";
                leaf username {
                  tailf:info
                    "Specify the username";
                  tailf:cli-incomplete-command;
                  type string {
                    length "1..31";
                    tailf:info
                      "WORD<length:1-31>;;Username";
                  }
                }
                container password {
                  tailf:info
                    "Specify the user password";
                  tailf:cli-flatten-container;
                  tailf:cli-compact-syntax;
                  choice ftp-pass-choice {
                    leaf cleartext {
                      tailf:cli-drop-node-name;
                      tailf:cli-disallow-value "encrypted";
                      type string {
                        length "0..31";
                        tailf:info
                          "WORD<length:0-31>;;Password, '' means empty password";
                      }
                    }
                    leaf encrypted {
                      tailf:info
                        "Do NOT use this option manually. (This is an A10 reserved keyword.)";
                      type string {
                        length "1..255";
                        tailf:info
                          "WORD<length:1-255>;;The ENCRYPTED password string";
                      }
                    }
                  }
                }
              }
            }
            container ldap {
              tailf:info
                "LDAP type";
              tailf:cli-compact-syntax;
              leaf port {
                tailf:info
                  "Specify the LDAP Port";
                tailf:cli-reset-container;
                type uint16 {
                  range "1..65534";
                  tailf:info
                    "<1-65534>;;Port Number (default 389, or 636 if LDAP over SSL)";
                }
              }
              leaf overssl {
                tailf:info
                  "LDAP over TLS";
                tailf:cli-reset-container;
                type empty;
              }
              container binddn {
                tailf:info
                  "Specify the Distinguished Name for bindRequest";
                tailf:cli-flatten-container;
                tailf:cli-compact-syntax;
                tailf:cli-sequence-commands {
                  tailf:cli-reset-siblings;
                }
                leaf name {
                  tailf:cli-drop-node-name;
                  type string {
                    length "1..63";
                    tailf:info
                      "WORD<length:1-63>;;LDAP DN distinguished name";
                  }
                }
                container password {
                  tailf:info
                    "Specify the password of simple authentication";
                  tailf:cli-flatten-container;
                  tailf:cli-compact-syntax;
                  tailf:cli-reset-container;
                  choice ftp-pass-choice {
                    leaf cleartext {
                      tailf:cli-drop-node-name;
                      tailf:cli-disallow-value "encrypted";
                      type string {
                        length "0..31";
                        tailf:info
                          "WORD<length:0-31>;;Password, '' means empty password";
                      }
                    }
                    leaf encrypted {
                      tailf:info
                        "Do NOT use this option manually. (This is an A10 reserved keyword.)";
                      type string {
                        length "1..255";
                        tailf:info
                          "WORD<length:1-255>;;The ENCRYPTED password string";
                      }
                    }
                  }
                }
              }
            }
            container rtsp {
              tailf:info
                "RTSP type";
              tailf:cli-compact-syntax;
              leaf port {
                tailf:info
                  "Specify RTSP port";
                tailf:cli-reset-container;
                type uint16 {
                  range "1..65534";
                  tailf:info
                    "<1-65534>;;Port Number (default 554)";
                }
              }
              leaf rtspurl {
                tailf:info
                  "URL string";
                tailf:cli-reset-container;
                type string {
                  length "1..127";
                  tailf:info
                    "WORD<length:1-127>;;Specifies the path on the server";
                }
              }
            }
            container database {
              tailf:info
                "DATABASE type";
              tailf:cli-compact-syntax;
              tailf:cli-sequence-commands {
                tailf:cli-reset-siblings;
              }
              leaf dbtype {
                tailf:cli-drop-node-name;
                tailf:cli-incomplete-command;
                type enumeration {
                  enum "mssql" {
                    tailf:info
                      "Specify MSSQL database";
                  }
                  enum "mysql" {
                    tailf:info
                      "Specify MySQL database";
                  }
                  enum "oracle" {
                    tailf:info
                      "Specify Oracle database";
                  }
                  enum "postgresql" {
                    tailf:info
                      "Specify PostgreSQL database";
                  }
                }
              }
              leaf db-name {
                tailf:info
                  "Specify the database name";
                tailf:cli-incomplete-command;
                when "../dbtype" {
                  tailf:xpath-root 3;
                  tailf:dependency "../dbtype";
                }
                mandatory true;
                type string {
                  length "1..31";
                  tailf:info
                    "WORD<length:1-31>;;Database name";
                }
              }
              leaf username {
                tailf:cli-incomplete-command;
                when "../dbtype" {
                  tailf:xpath-root 3;
                  tailf:dependency "../dbtype";
                }
                mandatory true;
                tailf:info
                  "Specify the username";
                type string {
                  length "1..31";
                  tailf:info
                    "WORD<length:1-31>;;Username";
                }
              }
              container password {
                tailf:info
                  "Specify the password of simple authentication";
                tailf:cli-flatten-container;
                tailf:cli-compact-syntax;
                when "../dbtype" {
                  tailf:xpath-root 3;
                  tailf:dependency "../dbtype";
                }
                choice db-pass-choice {
                  leaf cleartext {
                    tailf:cli-drop-node-name;
                    tailf:cli-disallow-value "encrypted";
                    tailf:cli-reset-container;
                    type string {
                      length "0..31";
                      tailf:info
                        "WORD<length:0-31>;;Password, '' means empty password";
                    }
                  }
                  leaf encrypted {
                    tailf:info
                      "Do NOT use this option manually. (This is an A10 reserved keyword.)";
                    tailf:cli-reset-container;
                    type string {
                      length "1..255";
                      tailf:info
                        "WORD<length:1-255>;;The ENCRYPTED password string";
                    }
                  }
                }
              }
              leaf send {
                tailf:info
                  "Specify the SQL query";
                type string {
                  length "1..63";
                  tailf:info
                    "WORD<length:1-63>  Specify the SQL query";
                }
              }
              leaf receive {
                tailf:info
                  "Specify the response string";
                type string {
                  length "1..31";
                  tailf:info
                    "WORD<length:1-31>;;Specify the response string";
                }
              }
              leaf row {
                tailf:info
                  "Specify the row number for receiving";
                type uint8 {
                  range "1..10";
                  tailf:info
                    "<1-10>;;Specify the row number for receiving";
                }
              }
              leaf column {
                tailf:info
                  "Specify the column number for receiving";
                type uint8 {
                  range "1..10";
                  tailf:info
                    "<1-10>;;Specify the column number for receiving";
                }
              }
            }
            container external {
              tailf:info
                "EXTERNAL type";
            }
            container ntp {
              tailf:info
                "NTP type";
            }
            container compound {
              tailf:info
                "Compound type";
            }
          }
        }
      }
    }
    leaf stats-data-disable {
      tailf:ncs-device-type "cli-ned";
      tailf:display-when "not(../../ncs:module) or ../../ncs:module[ncs:name='tailf-ned-a10-acos']";
      tailf:info
        "Disable global statistical data collection";
      tailf:cli-full-command;
      type empty;
    }
    container syn-cookie {
      tailf:ncs-device-type "cli-ned";
      tailf:display-when "not(../../ncs:module) or ../../ncs:module[ncs:name='tailf-ned-a10-acos']";
      tailf:cli-compact-syntax;
      tailf:cli-sequence-commands {
        tailf:cli-reset-siblings;
      }
      leaf on-threshold {
        type uint32;
      }
      leaf off-threshold {
        type uint32;
      }
    }
    container slb {
      tailf:ncs-device-type "cli-ned";
      tailf:display-when "not(../../ncs:module) or ../../ncs:module[ncs:name='tailf-ned-a10-acos']";
      tailf:info
        "SLB Commands";
      container graceful-shutdown {
        tailf:info
          "enable graceful shutdown";
        tailf:cli-sequence-commands {
          tailf:cli-reset-siblings;
        }
        tailf:cli-compact-syntax;
        leaf timeout {
          tailf:cli-drop-node-name;
          type uint16 {
            range "1..65535";
            tailf:info
              "<1-65535>;;1-65535, in unit of seconds";
          }
        }
        leaf when {
          must "../timeout" {
            tailf:xpath-root 3;
            tailf:dependency "../timeout";
          }
          tailf:cli-drop-node-name;
          type enumeration {
            enum "after-disable" {
              tailf:info
                "Graceful shutdown after disable server/port and/or virtual server/port";
            }
            enum "server" {
              tailf:info
                "Graceful shutdown server/port only";
            }
            enum "virtual-server" {
              tailf:info
                "Graceful shutdown virtual server/port only";
            }
          }
        }
      }
      container buff-thresh {
        tailf:info
          "set buffer threshhold";
        tailf:cli-sequence-commands {
          tailf:cli-reset-siblings;
        }
        tailf:cli-compact-syntax;
        leaf hw-buff {
          tailf:info
            "hw buffer threshhold";
          tailf:cli-incomplete-command;
          type uint32 {
            tailf:info
              "<0-2147483647>;;value1";
            range "0..2147483647";
          }
        }
        leaf relieve-thresh {
          tailf:cli-incomplete-command;
          type uint32 {
            tailf:info
              "<0-2147483647>;;value2";
            range "0..2147483647";
          }
        }
        leaf sys-buff-low {
          tailf:info
            "low water mark of system buffer";
          tailf:cli-incomplete-command;
          type uint32 {
            tailf:info
              "<0-2147483647>;;value3";
            range "0..2147483647";
          }
        }
        leaf sys-buff-high {
          tailf:info
            "high water mark of system buffer";
          type uint32 {
            tailf:info
              "<0-2147483647>;;value4";
            range "0..2147483647";
          }
        }
      }
      container template {
        tailf:info
          "Define an SLB template";
        list server {
          tailf:info
            "Server template";
          key "name";
          leaf name {
            type string {
              length "1..63";
              tailf:info
                "NAME<length:1-63>;;Server template name";
            }
          }
          leaf health-check {
            tailf:info
              "Check server's health status";
            tailf:cli-boolean-no;
            type boolean;
            default "true";
          }
          container conn-limit {
            tailf:info
              "Connection limit";
            tailf:cli-sequence-commands {
              tailf:cli-reset-siblings;
            }
            tailf:cli-compact-syntax;
            leaf limit {
              tailf:cli-drop-node-name;
              type uint32 {
                tailf:info
                  "<1-8000000>;;Connection limit";
                range "1..8000000";
              }
            }
            leaf resume {
              must "../limit" {
                tailf:xpath-root 3;
                tailf:dependency "../limit";
              }
              tailf:cli-optional-in-sequence;
              tailf:info
                "Resume accepting new connection after connection number drops below threshold";
              type uint32 {
                range "1..1048575";
                tailf:info
                  "<1-1048575>;;Connection resume threshold";
              }
            }
            leaf no-logging {
              tailf:info
                "Do not log connection over limit event";
              type empty;
            }
          }
          container conn-rate-limit {
            tailf:info
              "Connection rate limit";
            tailf:cli-sequence-commands {
              tailf:cli-reset-siblings;
            }
            tailf:cli-compact-syntax;
            leaf limit {
              tailf:cli-drop-node-name;
              type uint32 {
                tailf:info
                  "<1-1048575>;;Connection rate limit";
                range "1..1048575";
              }
            }
            leaf per {
              must "../limit" {
                tailf:xpath-root 3;
                tailf:dependency "../limit";
              }
              tailf:cli-optional-in-sequence;
              tailf:info
                "Resume accepting new connection after connection number drops below threshold";
              type enumeration {
                enum "100ms" {
                  tailf:info
                    "Use 100 ms as sampling interval";
                }
                enum "second" {
                  tailf:info
                    "Use 1 second as sampling interval";
                }
              }
            }
            leaf no-logging {
              tailf:info
                "Do not log connection over limit event";
              type empty;
            }
          }
          leaf dns-query-interval {
            tailf:cli-full-command;
            tailf:info
              "The interval to query DNS server for the hostname";
            type uint16 {
              range "1..1440";
              tailf:info
                "<1-1440>  DNS query interval (in minute, default is 10)";
            }
          }
          leaf dynamic-server-prefix {
            tailf:info
              "Prefix of dynamic server";
            tailf:cli-full-command;
            type string {
              length "1..3";
              tailf:info
                "WORD<length:1-3>  Prefix of dynamic server (default is 'DRS')";
            }
            default "DRS";
          }
          leaf max-dynamic-server {
            tailf:info
              "Maximum dynamic server number";
            tailf:cli-full-command;
            type uint16 {
              range "1..1023";
              tailf:info
                "<1-1023>;;Maximum dynamic server number (default is 255)";
            }
            default "255";
          }
          leaf min-ttl-ratio {
            tailf:info
              "Minimum TTL to DNS query interval ratio";
            tailf:cli-full-command;
            type uint16 {
              range "1..15";
              tailf:info
                "<1-15>;;Minimum TTL ratio (default is 2)";
            }
            default "2";
          }
          container slow-start {
            tailf:info
              "Slow ramp up the connection number after server is up";
            tailf:cli-sequence-commands {
              tailf:cli-reset-all-siblings;
            }
            tailf:cli-compact-syntax;
            leaf from {
              tailf:info
                "Initial slow start connection limit (default 128)";
              tailf:cli-optional-in-sequence;
              type uint16 {
                range "1..4095";
                tailf:info
                  "<1-4095>;;Initial slow start connection limit";
              }
            }
            choice slow-start-choice {
              leaf add {
                tailf:info
                  "Slow start connection limit add by a number every interval";
                tailf:cli-optional-in-sequence;
                type uint16 {
                  range "1..4095";
                  tailf:info
                    "<1-4095>  Add by this number every interval";
                }
              }
              leaf times {
                tailf:info
                  "Slow start connection limit multiply by a number every interval (default 2)";
                tailf:cli-optional-in-sequence;
                type uint8 {
                  range "2..10";
                  tailf:info
                    "<2-10>  Multiply by this number every interval";
                }
              }
            }
            leaf every {
              tailf:info
                "Slow start connection limit increment interval (default 10)";
              tailf:cli-optional-in-sequence;
              type uint8 {
                range "1..60";
                tailf:info
                  "<1-60>;;Slow start connection limit increment interval";
              }
            }
            leaf till {
              tailf:info
                "Slow start ends when slow start connection limit reaches a number (default 4096)";
              type uint16 {
                range "1..65535";
                tailf:info
                  "<1-65535>  Slow start ends when connection limit reaches this number";
              }
            }
          }
        }
        list port {
          tailf:info
            "Port template";
          key "name";
          leaf name {
            type string {
              length "1..63";
              tailf:info
                "NAME<length:1-63>;;Port template name";
            }
          }
          leaf health-check {
            tailf:info
              "Check server's health status";
            tailf:cli-boolean-no;
            type boolean;
            default "true";
          }
          container conn-limit {
            tailf:info
              "Connection limit";
            tailf:cli-sequence-commands {
              tailf:cli-reset-siblings;
            }
            tailf:cli-compact-syntax;
            leaf limit {
              tailf:cli-drop-node-name;
              type uint32 {
                tailf:info
                  "<1-8000000>;;Connection limit";
                range "1..8000000";
              }
            }
            leaf resume {
              must "../limit" {
                tailf:xpath-root 3;
                tailf:dependency "../limit";
              }
              tailf:cli-optional-in-sequence;
              tailf:info
                "Resume accepting new connection after connection number drops below threshold";
              type uint32 {
                range "1..1048575";
                tailf:info
                  "<1-1048575>;;Connection resume threshold";
              }
            }
            leaf no-logging {
              tailf:info
                "Do not log connection over limit event";
              type empty;
            }
          }
          container conn-rate-limit {
            tailf:info
              "Connection rate limit";
            tailf:cli-sequence-commands {
              tailf:cli-reset-siblings;
            }
            tailf:cli-compact-syntax;
            leaf limit {
              tailf:cli-drop-node-name;
              type uint32 {
                tailf:info
                  "<1-1048575>;;Connection rate limit";
                range "1..1048575";
              }
            }
            leaf per {
              must "../limit" {
                tailf:xpath-root 3;
                tailf:dependency "../limit";
              }
              tailf:cli-optional-in-sequence;
              tailf:info
                "Resume accepting new connection after connection number drops below threshold";
              type enumeration {
                enum "100ms" {
                  tailf:info
                    "Use 100 ms as sampling interval";
                }
                enum "second" {
                  tailf:info
                    "Use 1 second as sampling interval";
                }
              }
            }
            leaf no-logging {
              tailf:info
                "Do not log connection over limit event";
              type empty;
            }
          }
          leaf dest-nat {
            tailf:info
              "Destination NAT";
            tailf:cli-full-command;
            type empty;
          }
          leaf down-grace-period {
            tailf:info
              "Port down grace period";
            tailf:cli-full-command;
            type uint32 {
              tailf:info
                "<1-86400>;;Down grace period";
              range "1..86400";
            }
          }
          leaf dscp {
            tailf:info
              "Differentiated Services Code Point";
            tailf:cli-full-command;
            type uint8 {
              tailf:info
                "<1-63>  DSCP to Real Server IP Mapping Value";
              range "1..63";
            }
          }
          container dynamic-member-priority {
            tailf:cli-sequence-commands {
              tailf:cli-reset-siblings;
            }
            tailf:cli-compact-syntax;
            leaf priority {
              tailf:cli-drop-node-name;
              type uint8 {
                range "1..16";
                tailf:info
                  "<1-16>;;Initial priority (default bis 16)";
              }
            }
            leaf decrement {
              must "../priority" {
                tailf:xpath-root 3;
                tailf:dependency "../priority";
              }
              tailf:info
                "Decrement dynamic member's priority after every round of DNS query";
              type uint8 {
                range "0..7";
                tailf:info
                  "<0-7>  Decrement after every round of DNS query (default is 0)";
              }
            }
          }
          container inband-health-check {
            presence "true";
            tailf:cli-reset-container;
            tailf:info
              "Use inband traffic to detect port's health status";
            tailf:cli-sequence-commands {
              tailf:cli-reset-siblings;
            }
            tailf:cli-compact-syntax;
            leaf retry {
              tailf:info
                "Maximum retry times before reassign this connection to another server/port (default is 2)";
              tailf:cli-optional-in-sequence;
              type uint8 {
                range "0..7";
                tailf:info
                  "<0-7>;;The maximum retry number";
              }
            }
            leaf reassign {
              tailf:info
                "Maximum reassign times before declear the server/port down (default is 25)";
              type uint8 {
                range "0..255";
                tailf:info
                  "<0-255>;;The maximum reassign number";
              }
            }
          }
          container slow-start {
            tailf:info
              "Slow ramp up the connection number after port is up";
            tailf:cli-sequence-commands {
              tailf:cli-reset-all-siblings;
            }
            tailf:cli-compact-syntax;
            leaf from {
              tailf:info
                "Initial slow start connection limit (default 128)";
              tailf:cli-optional-in-sequence;
              type uint16 {
                range "1..4095";
                tailf:info
                  "<1-4095>;;Initial slow start connection limit";
              }
            }
            choice slow-start-choice {
              leaf add {
                tailf:info
                  "Slow start connection limit add by a number every interval";
                tailf:cli-optional-in-sequence;
                type uint16 {
                  range "1..4095";
                  tailf:info
                    "<1-4095>  Add by this number every interval";
                }
              }
              leaf times {
                tailf:info
                  "Slow start connection limit multiply by a number every interval (default 2)";
                tailf:cli-optional-in-sequence;
                type uint8 {
                  range "2..10";
                  tailf:info
                    "<2-10>  Multiply by this number every interval";
                }
              }
            }
            leaf every {
              tailf:info
                "Slow start connection limit increment interval (default 10)";
              tailf:cli-optional-in-sequence;
              type uint8 {
                range "1..60";
                tailf:info
                  "<1-60>;;Slow start connection limit increment interval";
              }
            }
            leaf till {
              tailf:info
                "Slow start ends when slow start connection limit reaches a number (default 4096)";
              type uint16 {
                range "1..65535";
                tailf:info
                  "<1-65535>  Slow start ends when connection limit reaches this number";
              }
            }
          }
          leaf source-nat {
            tailf:cli-full-command;
            tailf:info
              "Source NAT";
            type leafref {
              path "../../../../ip/nat/pool/name";
            }
          }
          leaf weight {
            tailf:cli-full-command;
            tailf:info
              "Weight";
            type uint8 {
              range "1..100";
              tailf:info
                "<1-100>;;port weight";
            }
          }
        }
        container cache {
          tailf:info
            "RAM caching template";
        }
        container client-ssl {
          tailf:info
            "Client SSL Template";
        }
        container connection-reuse {
          tailf:info
            "Connection Reuse";
        }
        container diameter {
          tailf:info
            "diameter template";
        }
        container dns {
          tailf:info
            "DNS template";
        }
        container http {
          tailf:info
            "HTTP";
        }
        container persist {
          tailf:info
            "Persistence";
          list source-ip {
            key "name";
            leaf name {
              type string {
                length "1..63";
                tailf:info
                  "NAME<length:1-63>;;Source IP persistence template name";
              }
            }
            leaf dont-honor-conn-rules {
              tailf:info
                "Do not observe connection rate rules";
              type empty;
              tailf:cli-full-command;
            }
            leaf enforce-higher-priority {
              tailf:info
                "Enforce to use high priority node if available";
              type empty;
              tailf:cli-full-command;
            }
            leaf incl-sport {
              tailf:info
                "include source port on the persist";
              type empty;
              tailf:cli-full-command;
            }
            container match-type {
              tailf:info
                "Persistence type";
              choice match-choice {
                container server {
                  presence "true";
                  tailf:cli-reset-container;
                  tailf:info
                    "Persist to the same server, default is port";
                  leaf scan-all-members {
                    tailf:info
                      "Persist with SCAN of all members";
                    type empty;
                  }
                }
                leaf service-group {
                  tailf:info
                    "Persist within the same service group";
                  type empty;
                }
              }
            }
            leaf netmask {
              tailf:info
                "IP subnet mask";
              type string {
                tailf:info
                  "/nn or A.B.C.D;;IP subnet mask";
              }
              tailf:cli-full-command;
            }
            leaf netmask6 {
              tailf:info
                "IPV6 subnet mask";
              type uint8 {
                range "1..128";
                tailf:info
                  "<1-128>;;number";
              }
              tailf:cli-full-command;
            }
            leaf timeout {
              tailf:info
                "Persistence timeout";
              type uint16 {
                range "1..2000";
                tailf:info
                  "<1-2000>;;in minutes";
              }
              tailf:cli-full-command;
            }
          }
        }
        container policy {
          tailf:info
            "Policy config";
        }
        container server-ssl {
          tailf:info
            "Server Side SSL Template";
        }
        container sip {
          tailf:info
            "SIP template";
        }
        container smtp {
          tailf:info
            "SMTP";
        }
        container streaming-media {
          tailf:info
            "Streaming media Template";
        }
        list tcp {
          tailf:info
            "L4 TCP switch config";
          key "name";
          leaf name {
            type string {
              length "1..63";
              tailf:info
                "NAME<length:1-63>;;Fast TCP Template Name";
            }
          }
          leaf idle-timeout {
            tailf:info
              "Idle Timeout value (default 120 seconds)";
            tailf:cli-full-command;
            type uint32 {
              range "60..120000";
              tailf:info
                "<60-120000>;;idle timeout in second, default 120";
            }
          }
          container force-delete-timeout {
            tailf:info
              "The maximum time that a session can stay in the system before being deleted";
            tailf:cli-sequence-commands {
              tailf:cli-reset-siblings;
            }
            tailf:cli-compact-syntax;
            leaf timeout {
              tailf:cli-drop-node-name;
              type uint8 {
                range "1..31";
                tailf:info
                  "<1-31>;;number (second)";
              }
            }
            leaf alive-if-active {
              tailf:info
                "keep connection alive if active traffic";
              must "../timeout" {
                tailf:xpath-root 3;
                tailf:dependency "../timeout";
              }
              type empty;
            }
          }
          leaf half-close-idle-timeout {
            tailf:info
              "TCP Half Close Idle Timeout (sec), default off";
            type uint16 {
              range "60..15000";
              tailf:info
                "<60-15000>;;half close idle timeout in second, default 120";
            }
          }
          leaf initial-window-size {
            tailf:info
              "Set the initial window size";
            type uint16 {
              range "1..65535";
              tailf:info
                "<1-65535>;;number";
            }
          }
          leaf lan-fast-ack {
            tailf:info
              "Enable fast TCP ack on LAN";
            type empty;
          }
          leaf reset-fwd {
            tailf:info
              "send reset to server if error happens";
            type empty;
          }
          leaf reset-rev {
            tailf:info
              "send reset to client if error happens";
            type empty;
          }
        }
        container tcp-proxy {
          tailf:info
            "TCP Proxy";
        }
        container udp {
          tailf:info
            "L4 UDP switch config";
        }
        container virtual-port {
          tailf:info
            "Virtual port template";
        }
        list virtual-server {
          tailf:info
            "Virtual server template";
          key "name";
          leaf name {
            type string {
              length "1..63";
              tailf:info
                "NAME<length:1-63>;;SLB Virtual Server template name";
            }
          }
          container conn-limit {
            tailf:info
              "Connection limit";
            tailf:cli-sequence-commands {
              tailf:cli-reset-siblings;
            }
            tailf:cli-compact-syntax;
            leaf limit {
              tailf:cli-drop-node-name;
              type uint32 {
                tailf:info
                  "<1-8000000>;;Connection limit";
                range "1..8000000";
              }
            }
            leaf reset {
              must "../limit" {
                tailf:xpath-root 3;
                tailf:dependency "../limit";
              }
              tailf:cli-optional-in-sequence;
              tailf:info
                "Send client reset when connection number over limit";
              type empty;
            }
            leaf no-logging {
              tailf:info
                "Do not log connection over limit event";
              type empty;
            }
          }
          container conn-rate-limit {
            tailf:info
              "Connection rate limit";
            tailf:cli-sequence-commands {
              tailf:cli-reset-siblings;
            }
            tailf:cli-compact-syntax;
            leaf limit {
              tailf:cli-drop-node-name;
              type uint32 {
                tailf:info
                  "<1-1048575>;;Connection rate limit";
                range "1..1048575";
              }
            }
            leaf per {
              must "../limit" {
                tailf:xpath-root 3;
                tailf:dependency "../limit";
              }
              tailf:cli-optional-in-sequence;
              tailf:info
                "Resume accepting new connection after connection number drops below threshold";
              type enumeration {
                enum "100ms" {
                  tailf:info
                    "Use 100 ms as sampling interval";
                }
                enum "second" {
                  tailf:info
                    "Use 1 second as sampling interval";
                }
              }
            }
            leaf reset {
              must "../limit" {
                tailf:xpath-root 3;
                tailf:dependency "../limit";
              }
              tailf:cli-optional-in-sequence;
              tailf:info
                "Send client reset when connection number over limit";
              type empty;
            }
            leaf no-logging {
              tailf:info
                "Do not log connection over limit event";
              type empty;
            }
          }
          container icmp-rate-limit {
            tailf:cli-sequence-commands {
              tailf:cli-reset-siblings;
            }
            tailf:cli-compact-syntax;
            tailf:info
              "ICMP rate limit";
            leaf rate {
              tailf:cli-drop-node-name;
              type uint16 {
                range "1..65535";
                tailf:info
                  "<1-65535>;;Normal rate limit. If exceeds this limit, drop the ICMP packet that goes over the limit";
              }
            }
            leaf lockup {
              must "../rate" {
                tailf:xpath-root 3;
                tailf:dependency "../rate";
              }
              tailf:info
                "Enter lockup state when ICMP rate exceeds lockup rate limit";
              type uint16 {
                range "1..65535";
                tailf:info
                  "<1-65535>;;Maximum rate limit. If exceeds this limit, drop all ICMP packet for a time period";
              }
              tailf:cli-incomplete-command;
            }
            leaf lockup-perio {
              tailf:cli-drop-node-name;
              must "../lockup" {
                tailf:xpath-root 3;
                tailf:dependency "../lockup";
              }
              type uint16 {
                range "1..65535";
                tailf:info
                  "Lockup period (second)";
              }
            }
          }
          leaf subnet-gratuitous-arp {
            tailf:info
              "Send gratuitous ARP for every IP in the subnet virtual server";
            type empty;
            tailf:cli-full-command;
          }
        }
      }
      list server {
        tailf:info
          "Server";
        key "name";
        unique "address";
        leaf name {
          type string {
            length "1..63";
            tailf:info
              "NAME<length:1-63>;;Server Name";
          }
        }
        leaf address {
          tailf:cli-drop-node-name;
          tailf:cli-hide-in-submode;
          tailf:cli-full-command;
          type union {
            type string {
              length "1..63";
              tailf:info
                "NAME<length:1-63>;;Server hostname";
            }
            type inet:ipv4-address {
              tailf:info
                "A.B.C.D;;IP Address";
            }
            type inet:ipv6-address {
              tailf:info
                "A:B:C:D:E:F:G:H;;IPV6 address";
            }
          }
        }
        container health-check {
          tailf:info
            "Health Check Monitor";
          leaf host {
            tailf:cli-drop-node-name;
            type leafref {
              path "/ncs:devices/ncs:device/ncs:config/a10-acos:health/monitor/name" {
                tailf:xpath-root 3;
              }
            }
          }
        }
        container conn-limit {
          tailf:info
            "Connection limit";
          tailf:cli-sequence-commands {
            tailf:cli-reset-siblings;
          }
          tailf:cli-compact-syntax;
          leaf limit {
            tailf:cli-drop-node-name;
            type uint32 {
              tailf:info
                "<1-8000000>;;Connection limit";
              range "1..8000000";
            }
          }
          leaf resume {
            must "../limit" {
              tailf:xpath-root 3;
              tailf:dependency "../limit";
            }
            tailf:cli-optional-in-sequence;
            tailf:info
              "Resume accepting new connection after connection number drops below threshold";
            type uint32 {
              range "1..1048575";
              tailf:info
                "<1-1048575>;;Connection resume threshold";
            }
          }
          leaf no-logging {
            tailf:info
              "Do not log connection over limit event";
            type empty;
          }
        }
        leaf conn-resume {
          tailf:info
            "Connection Resume";
          tailf:cli-full-command;
          type uint32 {
            tailf:info
              "<1-1000000>  Connection Resume (min active conn before resume taking new conn)";
            range "1..1000000";
          }
        }
        leaf extended-stats {
          tailf:info
            "Enable extended statistics on real server";
          tailf:cli-full-command;
          type empty;
        }
        leaf external-ip {
          tailf:info
            "External IP address for NAT of GSLB";
          tailf:cli-full-command;
          type inet:ipv4-address {
            tailf:info
              "A.B.C.D;;IP Address";
          }
        }
        container ha-priority-cost {
          tailf:info
            "Set a HA priority cost based on the real server's health";
          tailf:cli-sequence-commands {
            tailf:cli-reset-siblings;
          }
          tailf:cli-compact-syntax;
          leaf cost {
            tailf:cli-drop-node-name;
            type uint8 {
              range "1..255";
              tailf:info
                "Amount to subtract from the HA priority if the health-check fails";
            }
          }
          leaf ha-group {
            must "../cost" {
              tailf:xpath-root 3;
              tailf:dependency "../cost";
            }
            tailf:info
              "HA group to which the cost will apply (default: all)";
            type union {
              type enumeration {
                enum "all" {
                  tailf:info
                    "Apply to all HA groups";
                }
              }
              type uint8 {
                range "1..31";
                tailf:info
                  "<1-31>;;HA group number";
              }
            }
          }
        }
        leaf ipv6 {
          tailf:info
            "IPv6 address Mapping of GSLB";
          tailf:cli-full-command;
          type inet:ipv6-address {
            tailf:info
              "A:B:C:D:E:F:G:H;;IPV6 address";
          }
        }
        leaf slow-start {
          tailf:cli-full-command;
          tailf:info
            "Slowly ramp up the connection number after server is up (start from 128, then double every 10 sec till 4096)";
          type empty;
        }
        leaf spoofing-cache {
          tailf:cli-full-command;
          tailf:info
            "This server is a spoofing cache";
          type empty;
        }
        leaf stats-data-disable {
          tailf:info
            "Disable statistical data collection for real server";
          tailf:cli-full-command;
          type empty;
        }
        leaf weight {
          tailf:cli-full-command;
          tailf:info
            "Weight for this Real Server";
          type uint8 {
            range "1..100";
            tailf:info
              "<1-100>;;Connection weight";
          }
        }
        list port {
          tailf:info
            "Real Server Port";
          tailf:cli-full-command;
          key "number tcpudp";
          leaf number {
            type uint16 {
              range "0..65534";
              tailf:info
                "<0-65534>;;Port Number";
            }
          }
          leaf tcpudp {
            type enumeration {
              enum "tcp" {
                tailf:info
                  "TCP Port";
              }
              enum "udp" {
                tailf:info
                  "UDP Port";
              }
            }
          }
          container conn-limit {
            tailf:info
              "Connection limit";
            tailf:cli-sequence-commands {
              tailf:cli-reset-siblings;
            }
            tailf:cli-compact-syntax;
            leaf limit {
              tailf:cli-drop-node-name;
              type uint32 {
                tailf:info
                  "<1-8000000>;;Connection limit";
                range "1..8000000";
              }
            }
            leaf resume {
              must "../limit" {
                tailf:xpath-root 3;
                tailf:dependency "../limit";
              }
              tailf:cli-optional-in-sequence;
              tailf:info
                "Resume accepting new connection after connection number drops below threshold";
              type uint32 {
                range "1..1048575";
                tailf:info
                  "<1-1048575>;;Connection resume threshold";
              }
            }
            leaf no-logging {
              tailf:info
                "Do not log connection over limit event";
              type empty;
            }
          }
          leaf conn-resume {
            tailf:info
              "Connection Resume";
            tailf:cli-full-command;
            type uint32 {
              tailf:info
                "<1-1000000>  Connection Resume (min active conn before resume taking new conn)";
              range "1..1000000";
            }
          }
          leaf extended-stats {
            tailf:info
              "Enable extended statistics on real server";
            tailf:cli-full-command;
            type empty;
          }
          container ha-priority-cost {
            tailf:info
              "Set a HA priority cost based on the real server's health";
            tailf:cli-sequence-commands {
              tailf:cli-reset-siblings;
            }
            tailf:cli-compact-syntax;
            leaf cost {
              tailf:cli-drop-node-name;
              type uint8 {
                range "1..255";
                tailf:info
                  "Amount to subtract from the HA priority if the health-check fails";
              }
            }
            leaf ha-group {
              must "../cost" {
                tailf:xpath-root 3;
                tailf:dependency "../cost";
              }
              tailf:info
                "HA group to which the cost will apply (default: all)";
              type union {
                type enumeration {
                  enum "all" {
                    tailf:info
                      "Apply to all HA groups";
                  }
                }
                type uint8 {
                  range "1..31";
                  tailf:info
                    "<1-31>;;HA group number";
                }
              }
            }
          }
          container health-check {
            tailf:info
              "Health Check Monitor";
            leaf host {
              tailf:cli-drop-node-name;
              type leafref {
                path "/ncs:devices/ncs:device/ncs:config/a10-acos:health/monitor/name" {
                  tailf:xpath-root 3;
                }
              }
            }
          }
          leaf no-ssl {
            tailf:info
              "no-ssl";
            tailf:cli-full-command;
            type empty;
          }
          leaf stats-data-disable {
            tailf:info
              "Disable statistical data collection for real server port";
            tailf:cli-full-command;
            type empty;
          }
        }
        container template {
          tailf:info
            "Apply template to server";
          leaf server {
            tailf:info
              "Server template";
            type leafref {
              path "../../../../slb/template/server/name";
            }
          }
        }
      }
      list service-group {
        tailf:info
          "Service Group";
        tailf:cli-remove-before-change;
        key "name";
        leaf name {
          type string {
            length "1..63";
            tailf:info
              "NAME<length:1-63>;;SLB Service Name";
          }
        }
        leaf tcpudp {
          mandatory true;
          tailf:cli-drop-node-name;
          tailf:cli-hide-in-submode;
          type enumeration {
            enum "tcp" {
              tailf:info
                "TCP LB service";
            }
            enum "udp" {
              tailf:info
                "UDP LB service";
            }
          }
        }
        leaf backup-server-event-log {
          tailf:info
            "Send log info on back up server events";
          tailf:cli-full-command;
          type empty;
        }
        leaf extended-stats {
          tailf:info
            "Send log info on back up server events";
          tailf:cli-full-command;
          type empty;
        }
        container health-check {
          tailf:info
            "Health Check Monitor";
          leaf host {
            tailf:cli-drop-node-name;
            type leafref {
              path "/ncs:devices/ncs:device/ncs:config/a10-acos:health/monitor/name" {
                tailf:xpath-root 3;
              }
            }
          }
        }
        list member {
          tailf:info
            "Service Group Member";
          tailf:cli-suppress-mode;
          tailf:cli-key-format "$(1):$(2)";
          key "host port";
          leaf host {
            type leafref {
              path "../../../server/name";
            }
          }
          leaf port {
            type leafref {
              path "deref(../host)/../port/number";
            }
          }
        }
        container method {
          tailf:info
            "Load Balancing Method, Default is Round-Robin";
          choice method-choice {
            leaf fastest-response {
              tailf:info
                "Fastest response time on service port level";
              type empty;
            }
            container least-connection {
              tailf:info
                "Least connection on server level";
              presence "true";
              tailf:cli-reset-container;
              leaf pseudo-round-robin {
                tailf:info
                  "PRR, select the oldest node for sub-select";
                type empty;
              }
            }
            leaf least-request {
              tailf:info
                "Least request on service port level";
              type empty;
            }
            leaf round-robin {
              tailf:info
                "round robin on server level";
              type empty;
            }
            leaf round-robin-strict {
              tailf:info
                "strict round robin on server level";
              type empty;
            }
            container service-least-connection {
              tailf:info
                "Least connection on service port level";
              presence "true";
              tailf:cli-reset-container;
              leaf pseudo-round-robin {
                tailf:info
                  "PRR, select the oldest node for sub-select";
                type empty;
              }
            }
            container service-weighted-least-connection {
              tailf:info
                "Weighted least connection on service port level";
              presence "true";
              tailf:cli-reset-container;
              leaf pseudo-round-robin {
                tailf:info
                  "PRR, select the oldest node for sub-select";
                type empty;
              }
            }
            leaf stateless-dst-ip-hash {
              tailf:info
                "Stateless load-balancing based on Dst IP and Dst port hash";
              type empty;
            }
            leaf stateless-per-pkt-round-robin {
              tailf:info
                "Stateless load-balancing using per-packet round-robin";
              type empty;
            }
            leaf stateless-src-dst-ip-hash {
              tailf:info
                "Stateless load-balancing based on Src and Dst IP hash";
              type empty;
            }
            leaf stateless-src-ip-hash {
              tailf:info
                "Stateless load-balancing based on Src IP and Src port hash";
              type empty;
            }
            leaf stateless-src-ip-only-hash {
              tailf:info
                "Stateless load-balancing based on only Src IP hash";
              type empty;
            }
            container weighted-least-connection {
              tailf:info
                "Weighted least connection on server level";
              presence "true";
              tailf:cli-reset-container;
              leaf pseudo-round-robin {
                tailf:info
                  "PRR, select the oldest node for sub-select";
                type empty;
              }
            }
            leaf weighted-rr {
              tailf:info
                "Weighted round robin on server level";
              type empty;
            }
          }
        }
        container min-active-member {
          tailf:info
            "Minimum Active Member Per Priority";
          tailf:cli-sequence-commands {
            tailf:cli-reset-siblings;
          }
          tailf:cli-compact-syntax;
          leaf min {
            tailf:cli-drop-node-name;
            type uint8 {
              range "1..63";
              tailf:info
                "<1-63>  Minimum Active Member before Action";
            }
          }
          leaf method {
            must "../min" {
              tailf:xpath-root 3;
              tailf:dependency "../min";
            }
            tailf:cli-drop-node-name;
            type enumeration {
              enum "dynamic-priority" {
                tailf:info
                  "dynamic change member priority to met the min-active-member requirement";
              }
              enum "skip-pri-set" {
                tailf:info
                  "Skip Current Priority Set If Min not met";
              }
            }
          }
        }
        container priority {
          tailf:info
            "Priority option. Define different action for each priority node.";
          tailf:cli-sequence-commands {
            tailf:cli-reset-siblings;
          }
          tailf:cli-compact-syntax;
          leaf prio {
            tailf:cli-drop-node-name;
            type uint8 {
              range "1..16";
              tailf:info
                "<1-16>;;Priority in the Group";
            }
          }
          leaf action {
            tailf:cli-drop-node-name;
            type enumeration {
              enum "drop" {
                tailf:info
                  "Drop request when all priority nodes fail";
              }
              enum "drop-if-exceed-limit" {
                tailf:info
                  "Drop request when connection over limit";
              }
              enum "proceed" {
                tailf:info
                  "Proceed to next priority when all priority nodes fail(default)";
              }
              enum "reset" {
                tailf:info
                  "Send client reset when all priority nodes fail";
              }
              enum "reset-if-exceed-limit" {
                tailf:info
                  "Send client reset when connection over limit";
              }
            }
          }
        }
        container priority-affinity {
          tailf:info
            "Priority affinity. Persist to the same priority if possible.";
          presence "true";
        }
        leaf reset-on-server-selection-fail {
          tailf:info
            "Send reset to client if server selection fails";
          tailf:cli-full-command;
          type empty;
        }
        leaf stats-data-disable {
          tailf:info
            "Disable statistical data collection for servic group";
          tailf:cli-full-command;
          type empty;
        }
      }
      list virtual-server {
        tailf:info
          "Create a Virtual Server";
        key "name address";
        unique "address";
        leaf name {
          type string {
            length "1..63";
            tailf:info
              "NAME<length:1-63>;;SLB Virtual Server Name";
          }
        }
        leaf address {
          type union {
            type inet:ipv4-address {
              tailf:info
                "A.B.C.D;;IP Address";
            }
            type inet:ipv6-address {
              tailf:info
                "A:B:C:D:E:F:G:H;;IPV6 address";
            }
          }
        }
        leaf netmask {
          tailf:cli-drop-node-name;
          tailf:cli-hide-in-submode;
          type string {
            tailf:info
              "/nn or A.B.C.D;;IP subnet mask";
          }
        }
        leaf acl {
          tailf:cli-hide-in-submode;
          type uint8 {
            range "1..199";
            tailf:info
              "<1-199>;;acl id";
          }
        }
        leaf arp-disable {
          tailf:cli-full-command;
          tailf:info
            "Disable Respond to Virtual Server ARP request";
          type empty;
        }
        leaf disable {
          tailf:cli-full-command;
          tailf:info
            "Disable Virtual Server";
          type empty;
        }
        leaf extended-stats {
          tailf:info
            "Enable extended statistics on real server";
          tailf:cli-full-command;
          type empty;
        }
        leaf ha-dynamic {
          tailf:cli-full-command;
          tailf:info
            "dynamic failover based on vip status";
          type uint8 {
            range "1..255";
            tailf:info
              "<1-255>;;1-255";
          }
        }
        leaf ha-group {
          tailf:cli-full-command;
          tailf:info
            "Join a Failover Group";
          type uint8 {
            range "1..31";
            tailf:info
              "<1-31>;;1-31";
          }
        }
        leaf redistribution-flagged {
          tailf:info
            "Flag VIP for special redistribution handling";
          tailf:cli-full-command;
          type empty;
        }
        leaf stats-data-disable {
          tailf:info
            "Disable statistical data collection for virtual server";
          tailf:cli-full-command;
          type empty;
        }
        leaf vrid {
          tailf:cli-full-command;
          tailf:info
            "Join a vrrp group";
          type uint8 {
            range "1..31";
            tailf:info
              "<1-31>;;1 - 31";
          }
        }
        list port {
          tailf:info
            "Virtual Port";
          tailf:cli-remove-before-change;
          tailf:cli-incomplete-command;
          key "id";
          must "type != 'other' or id = 0" {
            tailf:xpath-root 3;
            tailf:dependency "id";
            tailf:dependency "type";
          }
          leaf id {
            type uint16 {
              range "0..65534";
              tailf:info
                "<0-65534>;;Port";
            }
          }
          leaf type {
            tailf:cli-drop-node-name;
            tailf:cli-hide-in-submode;
            mandatory true;
            type enumeration {
              enum "diameter" {
                tailf:info
                  "diameter port";
              }
              enum "dns-udp" {
                tailf:info
                  "DNS service over UDP";
              }
              enum "fast-http" {
                tailf:info
                  "Fast HTTP Port";
              }
              enum "ftp" {
                tailf:info
                  "File Transfer Protocol Port";
              }
              enum "http" {
                tailf:info
                  "HTTP Port";
              }
              enum "https" {
                tailf:info
                  "HTTPS port";
              }
              enum "mms" {
                tailf:info
                  "Microsoft Multimedia Service Port";
              }
              enum "others" {
                tailf:info
                  "for no tcp/udp protocol, do IP load balancing";
              }
              enum "rtsp" {
                tailf:info
                  "Real Time Streaming Protocol Port";
              }
              enum "sip" {
                tailf:info
                  "Session initiation protocol over UDP";
              }
              enum "sip-tcp" {
                tailf:info
                  "Session initiation protocol over TCP";
              }
              enum "sips" {
                tailf:info
                  "Session initiation protocol over TLS";
              }
              enum "smtp" {
                tailf:info
                  "SMTP Port";
              }
              enum "ssl-proxy" {
                tailf:info
                  "Generic SSL proxy";
              }
              enum "tcp" {
                tailf:info
                  "TCP LB service";
              }
              enum "tcp-proxy" {
                tailf:info
                  "Generic TCP proxy";
              }
              enum "tftp" {
                tailf:info
                  "TFTP Port";
              }
              enum "udp" {
                tailf:info
                  "UDP Port";
              }
            }
          }
          container access-list {
            tailf:info
              "Apply ACL rules to this Virtual Port";
            tailf:cli-sequence-commands {
              tailf:cli-reset-siblings;
            }
            tailf:cli-compact-syntax;
            choice access-list-id {
              leaf acl-id {
                tailf:cli-drop-node-name;
                type leafref {
                  path "../../../../../access-list/id";
                }
              }
              leaf name {
                tailf:info
                  "Apply a IPv6 access list";
                type string {
                  length "1..16";
                  tailf:info
                    "WORD<length:1-16>;;Named Access List";
                }
              }
            }
            leaf source-nat-pool {
              tailf:info
                "Policy based Source NAT";
              type leafref {
                path "../../../../../ip/nat/pool/name";
                tailf:info
                  "WORD;;NAT Pool or Pool Group";
              }
            }
            leaf sequence-number {
              tailf:info
                "Specify ACL precedence";
              type uint8 {
                tailf:info
                  "<1-32>;;sequence-number";
                range "1..32";
              }
            }
          }
          leaf aflex {
            tailf:info
              "Bind aFleX Script to the Virtual Port";
            type string {
              length "1..63";
              tailf:info
                "NAME<length:1-63>;;aFleX Script Name";
            }
            tailf:cli-full-command;
          }
          container conn-limit {
            tailf:info
              "Connection limit";
            tailf:cli-sequence-commands {
              tailf:cli-reset-siblings;
            }
            tailf:cli-compact-syntax;
            leaf limit {
              tailf:cli-drop-node-name;
              type uint32 {
                tailf:info
                  "<1-8000000>;;Connection limit";
                range "1..8000000";
              }
            }
            leaf reset {
              must "../limit" {
                tailf:xpath-root 3;
                tailf:dependency "../limit";
              }
              tailf:cli-optional-in-sequence;
              tailf:info
                "Send client reset when connection number over limit";
              type empty;
            }
            leaf no-logging {
              tailf:info
                "Do not log connection over limit event";
              type empty;
            }
          }
          leaf def-selection-if-pref-failed {
            tailf:info
              "Use default server selection method if prefer method failed";
            type empty;
            tailf:cli-full-command;
          }
          leaf disable {
            tailf:info
              "Disable Virtual Port";
            type empty;
            tailf:cli-full-command;
          }
          leaf extended-stats {
            tailf:info
              "Enable extended statistics on virtual port";
            type empty;
            tailf:cli-full-command;
          }
          leaf ha-conn-mirror {
            tailf:info
              "Enable for HA Conn sync";
            type empty;
            tailf:cli-full-command;
            must "../type='tcp' or ../type='diameter' or ../type='ftp' or ../type='mms' or ../type='rtsp' or ../type='sip' or ../type='tftp' or ../type='udp'" {
              tailf:xpath-root 3;
              tailf:dependency "../type";
            }
          }
          leaf name {
            tailf:info
              "SLB Virtual Service Name";
            type string {
              length "1..63";
              tailf:info
                "NAME<length:1-63>;;SLB Virtual Service Name";
            }
            tailf:cli-full-command;
          }
          container no-dest-nat {
            tailf:info
              "Disable destination NAT";
            presence "true";
            tailf:cli-reset-container;
            leaf port-translation {
              tailf:info
                "Enable port translation under no-dest-nat";
              type empty;
            }
          }
          leaf pbslb {
            tailf:info
              "Configure policy based server load balancing";
            type empty;
            tailf:cli-full-command;
          }
          leaf reset-on-server-selection-fail {
            tailf:info
              "Send client reset when server selection fails";
            type empty;
            tailf:cli-full-command;
          }
          leaf service-group {
            tailf:info
              "Bind a Service Group to this Virtual Server";
            type leafref {
              path "../../../../slb/service-group/name";
            }
            tailf:cli-full-command;
          }
          leaf snat-on-vip {
            tailf:info
              "Enable source NAT traffic against VIP";
            type empty;
            tailf:cli-full-command;
          }
          container source-nat {
            tailf:info
              "Source NAT";
            choice source-nat-choice {
              container auto {
                presence "true";
                tailf:info
                  "Configure auto NAT for the vport";
                tailf:cli-reset-container;
                leaf precedence {
                  tailf:info
                    "Set auto nat pool as higher precedence for source-nat";
                  type empty;
                }
              }
              leaf pool {
                type leafref {
                  path "../../../../../ip/nat/pool/name";
                  tailf:info
                    "WORD;;NAT Pool or Pool Group";
                }
              }
            }
          }
          leaf stats-data-disable {
            tailf:info
              "Disable statistical data collection for virtual port";
            type empty;
            tailf:cli-full-command;
          }
          leaf syn-cookie {
            tailf:info
              "Enable syn-cookie";
            type empty;
            tailf:cli-full-command;
          }
          container use-default-if-no-server {
            tailf:info
              "Use default forwarding if server selection failed";
            presence "true";
            tailf:cli-reset-container;
            leaf sack {
              tailf:info
                "SACK permitted by real servers";
              type empty;
            }
          }
          leaf use-rcv-hop-for-resp {
            tailf:info
              "Use receive hop for response to client";
            type empty;
            tailf:cli-full-command;
          }
          container template {
            tailf:info
              "Applying Templates to Virtual Port";
            leaf diameter {
              tailf:info
                "Diameter Template";
              type string {
                length "1..63";
                tailf:info
                  "NAME<length:1-63>;;Server template name";
              }
            }
            container persist {
              tailf:info
                "Persistance Template";
              leaf destination-ip {
                tailf:info
                  "Destination IP persistence";
                type string {
                  length "1..63";
                  tailf:info
                    "NAME<length:1-63>;;Server template name";
                }
              }
              leaf source-ip {
                tailf:info
                  "Source IP persistence";
                type leafref {
                  path "../../../../../../slb/template/persist/source-ip/name";
                }
              }
              leaf ssl-sid {
                tailf:info
                  "SSL session ID persistance";
                type string {
                  length "1..63";
                  tailf:info
                    "NAME<length:1-63>;;Server template name";
                }
              }
            }
            leaf policy {
              tailf:info
                "Policy Template";
              type string {
                length "1..63";
                tailf:info
                  "NAME<length:1-63>;;Server template name";
              }
            }
            leaf tcp {
              tailf:info
                "L4 TCP Template";
              type string {
                length "1..63";
                tailf:info
                  "NAME<length:1-63>;;Server template name";
              }
            }
            leaf virtual-port {
              tailf:info
                "Virtual port template";
              type string {
                length "1..63";
                tailf:info
                  "NAME<length:1-63>;;Server template name";
              }
            }
          }
        }
        container template {
          tailf:info
            "Apply template to virtual-server";
          leaf logging {
            tailf:info
              "Logging template";
            type string {
              length "1..63";
              tailf:info
                "NAME<length:1-63>;;Server template name";
            }
          }
          leaf policy {
            tailf:info
              "Policy template";
            type string {
              length "1..63";
              tailf:info
                "NAME<length:1-63>;;Server template name";
            }
          }
          leaf virtual-server {
            tailf:info
              "Virtual server template";
            type leafref {
              path "../../../../slb/template/virtual-server/name";
            }
          }
        }
      }
    }
    container logging {
      tailf:ncs-device-type "cli-ned";
      tailf:display-when "not(../../ncs:module) or ../../ncs:module[ncs:name='tailf-ned-a10-acos']";
      tailf:info
        "System logging configuration";
      container auditlog {
        tailf:info
          "Set send auditlog to syslog host.";
      }
      container buffered {
        tailf:info
          "Set buffered logging parameters";
        leaf size {
          tailf:cli-drop-node-name;
          type uint32 {
            range "10000..50000";
            tailf:info
              "<10000-50000>, default 30000;;Logging buffer size(in items).";
          }
        }
        leaf severity {
          tailf:cli-drop-node-name;
          type enumeration {
            enum "emergency" {
              tailf:info
                "System unusable log messages      (severity=0)";
            }
            enum "alert" {
              tailf:info
                "Action must be taken immediately  (severity=1)";
            }
            enum "critical" {
              tailf:info
                "Critical conditions               (severity=2)";
            }
            enum "error" {
              tailf:info
                "Error conditions                  (severity=3)";
            }
            enum "warning" {
              tailf:info
                "Warning conditions                (severity=4)";
            }
            enum "notification" {
              tailf:info
                "Normal but significant conditions (severity=5)";
            }
            enum "information" {
              tailf:info
                "Informational messages            (severity=6)";
            }
            enum "debugging" {
              tailf:info
                "Debug level messages              (severity=7)";
            }
          }
        }
      }
      leaf console {
        tailf:info
          "Set logging level which sent to console";
        type enumeration {
          enum "emergency" {
            tailf:info
              "System unusable log messages      (severity=0)";
          }
          enum "alert" {
            tailf:info
              "Action must be taken immediately  (severity=1)";
          }
          enum "critical" {
            tailf:info
              "Critical conditions               (severity=2)";
          }
          enum "error" {
            tailf:info
              "Error conditions                  (severity=3)";
          }
          enum "warning" {
            tailf:info
              "Warning conditions                (severity=4)";
          }
          enum "notification" {
            tailf:info
              "Normal but significant conditions (severity=5)";
          }
          enum "information" {
            tailf:info
              "Informational messages            (severity=6)";
          }
          enum "debugging" {
            tailf:info
              "Debug level messages              (severity=7)";
          }
        }
        tailf:cli-full-command;
      }
      container email {
        tailf:info
          "Set logging level which sent to email address";
        container buffer {
          tailf:info
            "Logging via email buffering settings";
          choice buffer-choice {
            leaf number {
              tailf:info
                "Number of log messages that can be buffered";
              type uint16 {
                range "16..256";
                tailf:info
                  "<16-256>;;Number of log messages that can be buffered, default 50";
              }
              default "50";
            }
            leaf time {
              tailf:info
                "Number of minutes a log message can stay in buffer";
              type uint16 {
                range "10..1440";
                tailf:info
                  "<10-1440>;;Number of minutes a log message can stay in buffer, default 10";
              }
              default "10";
            }
          }
        }
        leaf severity {
          tailf:cli-drop-node-name;
          type enumeration {
            enum "emergency" {
              tailf:info
                "System unusable log messages      (severity=0)";
            }
            enum "alert" {
              tailf:info
                "Action must be taken immediately  (severity=1)";
            }
            enum "critical" {
              tailf:info
                "Critical conditions               (severity=2)";
            }
            enum "notification" {
              tailf:info
                "Normal but significant conditions (severity=5)";
            }
          }
        }
      }
      leaf-list email-address {
        tailf:info
          "Set the recipients address";
        tailf:cli-flat-list-syntax;
        type string {
          tailf:info
            "WORD<length:1-63>;;Email address information of recipients";
        }
        tailf:cli-full-command;
      }
      leaf export {
        tailf:info
          "Export cached log items to the specified destination";
        type empty;
        tailf:cli-full-command;
      }
      leaf facility {
        tailf:info
          "Facility parameter for syslog messages";
        type enumeration {
          enum "local0" {
            tailf:info
              "Local use";
          }
          enum "local1" {
            tailf:info
              "Local use";
          }
          enum "local2" {
            tailf:info
              "Local use";
          }
          enum "local3" {
            tailf:info
              "Local use";
          }
          enum "local4" {
            tailf:info
              "Local use";
          }
          enum "local5" {
            tailf:info
              "Local use";
          }
          enum "local6" {
            tailf:info
              "Local use";
          }
          enum "local7" {
            tailf:info
              "Local use";
          }
        }
        tailf:cli-full-command;
      }
      leaf syslog {
        tailf:info
          "Set logging level which sent to syslog host";
        type enumeration {
          enum "emergency" {
            tailf:info
              "System unusable log messages      (severity=0)";
          }
          enum "alert" {
            tailf:info
              "Action must be taken immediately  (severity=1)";
          }
          enum "critical" {
            tailf:info
              "Critical conditions               (severity=2)";
          }
          enum "error" {
            tailf:info
              "Error conditions                  (severity=3)";
          }
          enum "warning" {
            tailf:info
              "Warning conditions                (severity=4)";
          }
          enum "notification" {
            tailf:info
              "Normal but significant conditions (severity=5)";
          }
          enum "information" {
            tailf:info
              "Informational messages            (severity=6)";
          }
          enum "debugging" {
            tailf:info
              "Debug level messages              (severity=7)";
          }
        }
        tailf:cli-full-command;
      }
      leaf trap {
        tailf:info
          "Set logging level which sent to snmp trap host";
        type enumeration {
          enum "emergency" {
            tailf:info
              "System unusable log messages      (severity=0)";
          }
          enum "alert" {
            tailf:info
              "Action must be taken immediately  (severity=1)";
          }
          enum "critical" {
            tailf:info
              "Critical conditions               (severity=2)";
          }
        }
        tailf:cli-full-command;
      }
      container host {
        tailf:info
          "Set remote syslog host DNS name or ip address";
        tailf:cli-sequence-commands {
          tailf:cli-reset-siblings;
        }
        tailf:cli-compact-syntax;
        leaf-list hosts {
          tailf:cli-flat-list-syntax;
          tailf:cli-drop-node-name;
          tailf:cli-optional-in-sequence;
          type string {
            tailf:info
              "Hostname or A.B.C.D  Remote syslog host DNS name or ip address";
          }
          tailf:cli-disallow-value "port";
        }
        leaf port {
          tailf:info
            "Set remote syslog port number,default is 514";
          type uint16 {
            range "1..32767";
            tailf:info
              "<1-32767>;;Remote syslog port number<1-32767>, default is 514";
          }
        }
      }
      leaf monitor {
        tailf:info
          "Set terminal monitor logging level";
        type enumeration {
          enum "emergency" {
            tailf:info
              "System unusable log messages      (severity=0)";
          }
          enum "alert" {
            tailf:info
              "Action must be taken immediately  (severity=1)";
          }
          enum "critical" {
            tailf:info
              "Critical conditions               (severity=2)";
          }
          enum "error" {
            tailf:info
              "Error conditions                  (severity=3)";
          }
          enum "warning" {
            tailf:info
              "Warning conditions                (severity=4)";
          }
          enum "notification" {
            tailf:info
              "Normal but significant conditions (severity=5)";
          }
          enum "information" {
            tailf:info
              "Informational messages            (severity=6)";
          }
          enum "debugging" {
            tailf:info
              "Debug level messages              (severity=7)";
          }
        }
        tailf:cli-full-command;
      }
    }
    container snmp-server {
      tailf:ncs-device-type "cli-ned";
      tailf:display-when "not(../../ncs:module) or ../../ncs:module[ncs:name='tailf-ned-a10-acos']";
      tailf:info
        "Modify SNMP engine parameters";
      container enable {
        tailf:info
          "Enable SNMP service or traps";
        leaf enabled {
          tailf:cli-drop-node-name;
          type empty;
        }
        container traps {
          tailf:info
            "Enable the traps";
          leaf enabled {
            tailf:cli-drop-node-name;
            type empty;
          }
          container routing {
            tailf:info
              "Enable A10 routing related SNMP traps";
            container ospf {
              choice routing-choice {
                leaf-list ospf-traps {
                  tailf:cli-drop-node-name;
                  tailf:cli-list-syntax;
                  type enumeration {
                    enum "ospfIfAuthFailure" {
                      tailf:info
                        "Enable ospfIfAuthFailure  ";
                    }
                    enum "ospfIfConfigError" {
                      tailf:info
                        "Enable ospfIfConfigError  ";
                    }
                    enum "ospfIfRxBadPacket" {
                      tailf:info
                        "Enable ospfIfRxBadPacket  ";
                    }
                    enum "ospfIfStateChange" {
                      tailf:info
                        "Enable ospfIfStateChange  ";
                    }
                    enum "ospfLsdbApproachingOverflow" {
                      tailf:info
                        "Enable ospfLsdbApproachingOverflow  ";
                    }
                    enum "ospfLsdbOverflow" {
                      tailf:info
                        "Enable ospfLsdbOverflow  ";
                    }
                    enum "ospfMaxAgeLsa" {
                      tailf:info
                        "Enable ospfMaxAgeLsa  ";
                    }
                    enum "ospfNbrStateChange" {
                      tailf:info
                        "Enable ospfNbrStateChange  ";
                    }
                    enum "ospfOriginateLsa" {
                      tailf:info
                        "Enable ospfOriginateLsa  ";
                    }
                    enum "ospfTxRetransmit" {
                      tailf:info
                        "Enable ospfTxRetransmit  ";
                    }
                    enum "ospfVirtIfAuthFailure" {
                      tailf:info
                        "Enable ospfVirtIfAuthFailure  ";
                    }
                    enum "ospfVirtIfConfigError" {
                      tailf:info
                        "Enable ospfVirtIfConfigError  ";
                    }
                    enum "ospfVirtIfRxBadPacket" {
                      tailf:info
                        "Enable ospfVirtIfRxBadPacket  ";
                    }
                    enum "ospfVirtIfStateChange" {
                      tailf:info
                        "Enable ospfVirtIfStateChange  ";
                    }
                    enum "ospfVirtIfTxRetransmit" {
                      tailf:info
                        "Enable ospfVirtIfTxRetransmit  ";
                    }
                    enum "ospfVirtNbrStateChange" {
                      tailf:info
                        "Enable ospfVirtNbrStateChange  ";
                    }
                  }
                }
                leaf all {
                  tailf:info
                    "Enable All Traps";
                  type empty;
                }
              }
            }
          }
          container snmp {
            tailf:info
              "Enable SNMP group traps";
            leaf enabled {
              tailf:cli-drop-node-name;
              type empty;
            }
            leaf linkdown {
              tailf:info
                "Enable SNMP link-down trap";
              type empty;
            }
            leaf linkup {
              tailf:info
                "Enable SNMP link-up trap";
              type empty;
            }
          }
          container ha {
            tailf:info
              "Enable HA group traps";
            leaf enabled {
              tailf:cli-drop-node-name;
              type empty;
            }
            leaf active {
              tailf:info
                "Enable HA active trap";
              type empty;
            }
            leaf active-active {
              tailf:info
                "Enable HA active-active trap";
              type empty;
            }
            leaf standby {
              tailf:info
                "Enable HA standby trap";
              type empty;
            }
            leaf vrrp {
              tailf:info
                "Enable HA vrrp traps";
              type empty;
            }
          }
          container network {
            tailf:info
              "Enable network group traps";
            leaf enabled {
              tailf:cli-drop-node-name;
              type empty;
            }
            leaf trunk-port-threshold {
              tailf:info
                "Enable network trunk-port-threshold trap";
              type empty;
            }
          }
          container slb {
            tailf:info
              "Enable SLB group traps";
            leaf enabled {
              tailf:cli-drop-node-name;
              type empty;
            }
            leaf application-buffer-limit {
              tailf:info
                "Enable application buffer reach limit trap";
              type empty;
            }
            leaf server-conn-limit {
              tailf:info
                "Enable SLB server connection limit trap";
              type empty;
            }
            leaf server-conn-resume {
              tailf:info
                "Enable SLB server connection resume trap";
              type empty;
            }
            leaf server-down {
              tailf:info
                "Enable SLB server-down trap";
              type empty;
            }
            leaf server-up {
              tailf:info
                "Enable SLB server-up trap";
              type empty;
            }
            leaf service-conn-limit {
              tailf:info
                "Enable SLB service connection limit trap";
              type empty;
            }
            leaf service-conn-resume {
              tailf:info
                "Enable SLB service connection resume trap";
              type empty;
            }
            leaf service-down {
              tailf:info
                "Enable SLB service-down trap";
              type empty;
            }
            leaf service-up {
              tailf:info
                "Enable SLB service-up trap";
              type empty;
            }
            leaf vip-connlimit {
              tailf:info
                "Enable the virtual server reach conn-limit trap";
              type empty;
            }
            leaf vip-connratelimit {
              tailf:info
                "Enable the virtual server reach conn-rate-limit trap";
              type empty;
            }
            leaf vip-port-connlimit {
              tailf:info
                "Enable the virtual port reach conn-limit trap";
              type empty;
            }
            leaf vip-port-connratelimit {
              tailf:info
                "Enable the virtual port reach conn-rate-limit trap";
              type empty;
            }
            leaf vip-port-down {
              tailf:info
                "Enable SLB virtual port down trap";
              type empty;
            }
            leaf vip-port-up {
              tailf:info
                "Enable SLB virtual port up trap";
              type empty;
            }
          }
          container system {
            tailf:info
              "Enable system group traps";
            leaf enabled {
              tailf:cli-drop-node-name;
              type empty;
            }
            leaf control-cpu-high {
              tailf:info
                "Enable control CPU usage high trap";
              type empty;
            }
            leaf data-cpu-high {
              tailf:info
                "Enable data CPU usage high trap";
              type empty;
            }
            leaf fan {
              tailf:info
                "Enable system fan trap";
              type empty;
            }
            leaf high-disk-use {
              tailf:info
                "Enable system high disk usage trap";
              type empty;
            }
            leaf high-memory-use {
              tailf:info
                "Enable system high memory usage trap";
              type empty;
            }
            leaf high-temp {
              tailf:info
                "Enable system high temperature trap";
              type empty;
            }
            leaf packet-drop {
              tailf:info
                "Enable system packet dropped trap";
              type empty;
            }
            leaf power {
              tailf:info
                "Enable system power supply trap";
              type empty;
            }
            leaf pri-disk {
              tailf:info
                "Enable system primary hard disk trap";
              type empty;
            }
            leaf restart {
              tailf:info
                "Enable system restart trap";
              type empty;
            }
            leaf sec-disk {
              tailf:info
                "Enable system secondary hard disk trap";
              type empty;
            }
            leaf shutdown {
              tailf:info
                "Enable system shutdown trap";
              type empty;
            }
            leaf start {
              tailf:info
                "Enable system start trap";
              type empty;
            }
          }
        }
      }
      leaf location {
        tailf:info
          "Text for mib object sysLocation";
        tailf:cli-full-command;
        type string {
          length "1..63";
          tailf:info
            "WORD<length:1-63>  The physical location of this node";
        }
      }
      list user {
        tailf:info
          "Define a user who can access the SNMP engine";
        tailf:cli-reset-container;
        tailf:cli-suppress-mode;
        key "name group type";
        leaf name {
          type string {
            length "1..31";
            tailf:info
              "WORD<length:1-31>;;Name of the user";
          }
        }
        leaf group {
          tailf:info
            "Group to which the user belongs";
          tailf:cli-expose-key-name;
          type string {
            tailf:info
              "WORD<length:1-31>;;Group to which the user belongs";
            length "1..31";
          }
        }
        leaf type {
          type enumeration {
            enum "v1" {
              tailf:info
                "User using the v1 security model";
            }
            enum "v2c" {
              tailf:info
                "User using the v2c security model";
            }
            enum "v3" {
              tailf:info
                "User using the v3 security model";
            }
          }
        }
        container auth {
          when "../type = 'v3'" {
            tailf:xpath-root 3;
            tailf:dependency "../type";
          }
          tailf:info
            "Authentication parameters for the user";
          tailf:cli-compact-syntax;
          tailf:cli-sequence-commands {
            tailf:cli-reset-siblings;
          }
          leaf mac {
            tailf:cli-drop-node-name;
            tailf:cli-incomplete-command;
            type enumeration {
              enum "MD5" {
                tailf:info
                  "Use HMAC MD5 algorithm for authentication";
              }
              enum "SHA" {
                tailf:info
                  "Use HMAC SHA algorithm for authentication";
              }
            }
          }
          leaf cleartext {
            tailf:cli-drop-node-name;
            tailf:cli-disallow-value "pw-encrypted";
            tailf:cli-optional-in-sequence;
            type string {
              tailf:info
                "WORD<length:8-31>  Password of this user";
              length "8..31";
            }
          }
          leaf pw-encrypted {
            when "../mac and not(../cleartext)" {
              tailf:xpath-root 3;
              tailf:dependency "../mac";
              tailf:dependency "../cleartext";
            }
            tailf:info
              "Do NOT use this option manually. (This is an A10 reserved keyword.)";
            type string {
              length "1..255";
              tailf:info
                "WORD<length:1-255>;;The ENCRYPTED password string";
            }
          }
          leaf encrypted {
            must "../pw-encrypted" {
              tailf:xpath-root 3;
              tailf:dependency "../pw-encrypted";
            }
            tailf:info
              "Specifying encrypt SNMP messages";
            type empty;
          }
        }
      }
      list view {
        key "name";
        leaf name {
          type string {
            length "1..31";
            tailf:info
              "WORD<length:1-31>;;Name of the view";
          }
        }
      }
      container group {
        tailf:info
          "Define a User Security Model group";
      }
      list community {
        tailf:info
          "Define a community who can access the SNMP engine";
        key "read remote";
        tailf:cli-suppress-mode;
        tailf:cli-compact-syntax;
        tailf:cli-reset-container;
        leaf read {
          tailf:cli-expose-key-name;
          tailf:info
            "read only community";
          type string {
            length "1..31";
            tailf:info
              "WORD<length:1-31>;;SNMPv1/v2c community string";
          }
        }
        leaf remote {
          tailf:cli-expose-key-name;
          tailf:info
            "Specify a remote SNMP entity to which the user belongs";
          type string {
            length "1..31";
            tailf:info
              "Hostname or A.B.C.D;;IP address of remote SNMP entity(length: 1-31)";
          }
        }
        leaf oid {
          tailf:info
            "specific the oid";
          tailf:cli-prefix-key {
            tailf:cli-before-key 2;
          }
          type string {
            length "1..31";
            tailf:info
              "WORD<length:1-31>;;The oid qvalue";
          }
        }
        leaf mask {
          tailf:cli-drop-node-name;
          type string {
            tailf:info
              "/nn or A.B.C.D;;The mask";
          }
        }
      }
      leaf contact {
        tailf:info
          "Text for mib object sysContact";
        tailf:cli-full-command;
        type string {
          length "1..63";
          tailf:info
            "WORD<length:1-63>;;Identification of the contact person for this managed node";
        }
      }
      list host {
        tailf:info
          "";
        tailf:cli-suppress-mode;
        tailf:cli-sequence-commands {
          tailf:cli-reset-siblings;
        }
        tailf:cli-compact-syntax;
        tailf:cli-incomplete-command;
        key "ip version";
        leaf ip {
          type string {
            tailf:info
              "Hostname or A.B.C.D;;IP address or hostname of SNMP trap host (length: 1-31)";
          }
        }
        leaf version {
          tailf:info
            "SNMP version to use for traps messages";
          tailf:cli-expose-key-name;
          type enumeration {
            enum "v1" {
              tailf:info
                "Use SNMPv1";
            }
            enum "v2c" {
              tailf:info
                "Use SNMPv2c";
            }
          }
        }
        leaf community-string {
          tailf:cli-drop-node-name;
          tailf:cli-incomplete-command;
          mandatory true;
          type string {
            length "1..31";
            tailf:info
              "WORD<length:1-31>  SNMPv1/v2c community string";
          }
        }
        leaf udp-port {
          mandatory true;
          type uint16 {
            tailf:info
              "<1-65535>;;The trap host's UDP port number(default: 162)";
            range "1..65535";
          }
        }
      }
    }
    container terminal {
      tailf:ncs-device-type "cli-ned";
      tailf:display-when "not(../../ncs:module) or ../../ncs:module[ncs:name='tailf-ned-a10-acos']";
      tailf:info
        "Set Terminal Startup Parameters";
      leaf auto-size {
        tailf:info
          "Enable terminal length and width automatically (not work if width or length set to 0)";
        tailf:cli-full-command;
        type empty;
      }
      leaf editing {
        tailf:info
          "Enable command line editing";
        tailf:cli-full-command;
        type empty;
      }
      container history {
        tailf:info
          "Enable and control the command history function";
        leaf size {
          tailf:info
            "Set history buffer size";
          type uint16 {
            range "1..1000";
            tailf:info
              "<0-1000>;;Size of history buffer, default is 256";
          }
          default "256";
        }
      }
      leaf idle-timeout {
        tailf:cli-full-command;
        tailf:info
          "Set interval for closing connection when there is no input detected";
        type uint8 {
          range "0..60";
          tailf:info
            "<0-60>;;Timeout in minutes, 0 means never timeout, default is 10";
        }
      }
      leaf length {
        tailf:info
          "Set number of lines on a screen(0 for no pausing)";
        tailf:cli-full-command;
        type uint16 {
          range "0..512";
          tailf:info
            "<0-512>;;Number of lines on screen, 0 for no pausing, default is 24";
        }
      }
      leaf no-ha-prompt {
        tailf:info
          "disable the ha status prompt function";
        tailf:cli-full-command;
        type empty;
      }
      leaf width {
        tailf:info
          "Set width of the display terminal";
        tailf:cli-full-command;
        type uint16 {
          range "0..512";
          tailf:info
            "<0-512>;;Number of characters on a screen line, 0 means infinite, default is 80";
        }
      }
    }
    container authentication {
      tailf:ncs-device-type "cli-ned";
      tailf:display-when "not(../../ncs:module) or ../../ncs:module[ncs:name='tailf-ned-a10-acos']";
      tailf:info
        "Configure authentication feature";
      leaf-list type {
        tailf:info
          "The authentication type";
        tailf:cli-flat-list-syntax;
        type enumeration {
          enum "tacplus" {
            tailf:info
              "The tacplus authentication type";
          }
          enum "radius" {
            tailf:info
              "The RADIUS authentication type";
          }
          enum "local" {
            tailf:info
              "The local authentication type";
          }
        }
      }
      container console {
        tailf:info
          "Configure console authentication type";
        leaf-list type {
          tailf:info
            "The authentication type";
          type enumeration {
            enum "tacplus" {
              tailf:info
                "The tacplus authentication type";
            }
            enum "radius" {
              tailf:info
                "The RADIUS authentication type";
            }
            enum "local" {
              tailf:info
                "The local authentication type";
            }
          }
        }
      }
      leaf disable-local {
        tailf:info
          "Disable the local authentication when the external authentication is available";
        tailf:cli-full-command;
        type empty;
      }
    }
    leaf enable-core {
      tailf:ncs-device-type "cli-ned";
      tailf:display-when "not(../../ncs:module) or ../../ncs:module[ncs:name='tailf-ned-a10-acos']";
      tailf:info
        "Enable system coredump switch";
      tailf:cli-full-command;
      type empty;
    }
  }
  augment "/ncs:devices/ncs:template/ncs:config" {
    container vrrp-a {
      leaf device-id {
        type string;
      }
      leaf disable-default-vrid {
        type empty;
      }
      leaf enable {
        type empty;
      }
      leaf set-id {
        type string;
      }
      list vrid {
        // NCS patched for predictable order
        ordered-by user;
        key "id";
        leaf id {
          type string;
        }
        leaf floating-ip {
          type string;
        }
        leaf priority {
          type string;
        }
        container preempt-mode {
          choice preempt-choice {
            leaf disable {
              type empty;
            }
            leaf threshhold {
              type string;
            }
          }
        }
        container tracking-options {

          grouping priority-cost {
            leaf priority-cost {
              // NCS drop mandatory statement
              type string;
            }
          }
          list gateway {
            // NCS patched for predictable order
            ordered-by user;
            key "address";
            leaf address {
              type string;
            }
            uses priority-cost;
          }
          container interface {
            list ethernet {
              // NCS patched for predictable order
              ordered-by user;
              key "id";
              leaf id {
                type string;
              }
              uses priority-cost;
            }
          }
          list route {
            // NCS patched for predictable order
            ordered-by user;
            key "ip mask";
            leaf ip {
              type string;
            }
            leaf mask {
              type string;
            }
            uses priority-cost;
            leaf distance {
              type string;
            }
            leaf gateway {
              type string;
            }
            leaf protocol {
              type string;
            }
          }
          list trunk {
            // NCS patched for predictable order
            ordered-by user;
            key "id";
            leaf id {
              type string;
            }
            uses priority-cost;
          }
          list vlan {
            // NCS patched for predictable order
            ordered-by user;
            key "id";
            leaf id {
              type string;
            }
            leaf timeout {
              type string;
            }
            uses priority-cost;
          }
        }
      }
      container interface {
        list ethernet {
          // NCS patched for predictable order
          ordered-by user;
          key "id";
          leaf id {
            type string;
          }
          choice vrrp-a-ethernet-choice {
            leaf both {
              type empty;
            }
            leaf no-heartbeat {
              type empty;
            }
            container router-interface {
              choice vrrp-a-r-i-choice {
                leaf no-heartbeat {
                  type empty;
                }
                leaf vlan {
                  type string;
                }
              }
            }
            container server-interface {
              presence "true";
              choice vrrp-a-s-i-choice {
                leaf no-heartbeat {
                  type empty;
                }
                leaf vlan {
                  type string;
                }
              }
            }
            leaf vlan {
              type string;
            }
          }
        }
      }
    }
    container ha {
      leaf arp-retry {
        type string;
      }
      container check {
        leaf gateway {
          type string;
        }
        list route {
          // NCS patched for predictable order
          ordered-by user;
          key "ip mask gateway distance priority-cost";
          leaf ip {
            type string;
          }
          leaf mask {
            type string;
          }
          leaf gateway {
            type string;
          }
          leaf distance {
            type string;
          }
          leaf protocol {
            type string;
            // NCS drop default statement
          }
          leaf priority-cost {
            type string;
          }
        }
        container vlan {
          leaf vlan-id {
            type string;
          }
          leaf timeout {
            // NCS drop must statement
            type string;
          }
        }
      }
      container conn-mirror {
        leaf ip {
          type string;
        }
      }
      container force-self-standby {
        presence "true";
        leaf HA-group-id {
          type string;
        }
      }
      leaf forward-l4-packet-on-standby {
        type empty;
      }
      list group {
        // NCS patched for predictable order
        ordered-by user;
        key "id";
        leaf id {
          type string;
        }
        leaf priority {
          // NCS drop must statement
          type string;
        }
      }
      container id {
        leaf id {
          type string;
        }
        leaf set-id {
          // NCS drop must statement
          type string;
        }
      }
      container inline-mode {
        presence "true";
        leaf preferred-port {
          type string;
        }
      }
      container interface {
        list ethernet {
          // NCS patched for predictable order
          ordered-by user;
          key "id";
          leaf id {
            type string;
          }
          leaf type {
            type string;
          }
          choice xx {
            leaf no-heartbeat {
              type empty;
            }
            leaf vlan {
              type string;
            }
          }
        }
      }
      leaf preemption-enable {
        type empty;
      }
    }
    leaf hostname {
      type string;
    }
    container clock {
      leaf timezone {
        type string;
      }
    }
    container ntp {
      list server {
        // NCS patched for predictable order
        ordered-by user;
        key "name";
        leaf name {
          type string;
        }
        leaf interval {
          type string;
        }
      }
    }
    container system {
      leaf module-ctrl-cpu {
        type string;
      }
      leaf glid {
        type string;
      }
      container all-vlan-limit {
        leaf bcast {
          type string;
        }
        leaf ipmcast {
          type string;
        }
        leaf mcast {
          type string;
        }
        leaf unknown-ucast {
          type string;
        }
      }
      container per-vlan-limit {
        leaf bcast {
          type string;
        }
        leaf ipmcast {
          type string;
        }
        leaf mcast {
          type string;
        }
        leaf unknown-ucast {
          type string;
        }
      }
      container resource-usage {
        leaf class-list-ipv6-addr-count {
          type string;
        }
        leaf client-ssl-template-count {
          type string;
        }
        leaf conn-reuse-template-count {
          type string;
        }
        leaf fast-tcp-template-count {
          type string;
        }
        leaf fast-udp-template-count {
          type string;
        }
        leaf http-template-count {
          type string;
        }
        leaf l4-session-count {
          type string;
        }
        leaf nat-pool-addr-count {
          type string;
        }
        leaf persist-cookie-template-count {
          type string;
        }
        leaf persist-srcip-template-count {
          type string;
        }
        leaf proxy-template-count {
          type string;
        }
        leaf real-port-count {
          type string;
        }
        leaf real-server-count {
          type string;
        }
        leaf server-ssl-template-count {
          type string;
        }
        leaf service-group-count {
          type string;
        }
        leaf stream-template-count {
          type string;
        }
        leaf virtual-port-count {
          type string;
        }
        leaf virtual-server-count {
          type string;
        }
      }
      container template {
        leaf policy {
          type string;
        }
      }
      leaf ve-mac-scheme {
        type string;
      }
    }
    list trunk {
      // NCS patched for predictable order
      ordered-by user;
      key "id";
      leaf id {
        type string;
      }
      container ethernet {
        leaf from {
          type string;
        }
        leaf to {
          // NCS drop must statement
          type string;
        }
      }
      leaf port-threshold {
        type string;
      }
      leaf port-threshold-timer {
        type string;
        // NCS drop default statement
      }
    }
    list vlan {
      // NCS patched for predictable order
      ordered-by user;
      key "id";
      leaf id {
        type string;
      }
      leaf name {
        type string;
      }
      container router-interface {
        leaf ve {
          type string;
        }
      }
      container untagged {
        container ethernet {
          leaf from {
            type string;
          }
          leaf to {
            // NCS drop must statement
            type string;
          }
        }
        leaf trunk {
          type string;
        }
      }
      container tagged {
        container ethernet {
          leaf from {
            type string;
          }
          leaf to {
            // NCS drop must statement
            type string;
          }
        }
        leaf trunk {
          type string;
        }
      }
    }
    list access-list {
      // NCS patched for predictable order
      ordered-by user;
      key "id";
      leaf id {
        type string;
      }
      list rules {
        // NCS patched for predictable order
        ordered-by user;
        key "txt";
        leaf txt {
          type string;
        }
      }
    }
    container radius-server {
      list host {
        // NCS patched for predictable order
        ordered-by user;
        key "name";
        leaf name {
          type string;
        }
        container secret {
          leaf cleartext {
            type string;
          }
          leaf secret-encrypted {
            // NCS drop when statement
            type string;
          }
        }
      }
    }
    container interface {
      container management {
        container ip {
          list address {
            // NCS patched for predictable order
            ordered-by user;
            key "ip";
            leaf ip {
              type string;
            }
            leaf mask {
              type string;
            }
          }
          leaf control-apps-use-mgmt-port {
            type empty;
          }
          leaf default-gateway {
            type string;
          }
        }
        container ipv6 {
          list address {
            // NCS patched for predictable order
            ordered-by user;
            key "ip";
            leaf ip {
              type string;
            }
            leaf link-local {
              type empty;
            }
          }
          leaf default-gateway {
            type string;
          }
        }
        leaf flow-control {
          type empty;
        }
        container access-list {
          leaf id {
            type string;
          }
          leaf in {
            // NCS drop must statement
            type empty;
          }
        }
        leaf enabled-disabled {
          type string;
          // NCS drop default statement
        }
        leaf duplexity {
          type string;
          // NCS drop default statement
        }
        leaf mtu {
          type string;
          // NCS drop default statement
        }
        leaf speed {
          type string;
          // NCS drop default statement
        }
      }
      list ethernet {
        // NCS patched for predictable order
        ordered-by user;
        key "nr";
        leaf nr {
          type string;
        }
        container access-list {
          leaf id {
            type string;
          }
          leaf in {
            // NCS drop must statement
            type empty;
          }
        }
        leaf enabled-disabled {
          type string;
          // NCS drop default statement
        }
        leaf duplexity {
          type string;
          // NCS drop default statement
        }
        leaf flow-control {
          type empty;
        }
        container icmp-rate-limit {
          leaf rate {
            type string;
          }
          leaf lockup {
            // NCS drop must statement
            type string;
          }
          leaf lockup-perio {
            // NCS drop must statement
            type string;
          }
        }
        container ip {
          list address {
            // NCS patched for predictable order
            ordered-by user;
            key "ip";
            leaf ip {
              type string;
            }
            leaf mask {
              // NCS drop must statement
              type string;
            }
          }
          leaf allow-promiscuous-vip {
            type empty;
          }
          leaf cache-spoofing-port {
            type empty;
          }
          leaf helper-address {
            type string;
          }
          container nat {
            leaf inside {
              type empty;
            }
            leaf outside {
              type empty;
            }
          }
          container ospf;
          container router {
            container isis {
              presence "true";
              leaf cmds {
                type string;
              }
            }
          }
          container tcp {
            leaf syn-cookie {
              type empty;
            }
          }
        }
        container ipv6 {
          container access-list {
            leaf id {
              type string;
            }
            leaf in {
              // NCS drop must statement
              type empty;
            }
          }
          list address {
            // NCS patched for predictable order
            ordered-by user;
            key "ip";
            leaf ip {
              type string;
            }
            leaf link-local {
              type empty;
            }
            leaf anycast {
              type empty;
            }
          }
          container nat {
            leaf inside {
              type empty;
            }
            leaf outside {
              type empty;
            }
          }
          container ndisc {
            container router-advertisement;
          }
          container ospf;
          container router {
            container isis {
              presence "true";
              leaf cmds {
                type string;
              }
            }
          }
        }
        container ospf;
        container isis;
        leaf l3-vlan-fwd-disable {
          type empty;
        }
        container lacp {
          leaf port-priority {
            type string;
          }
          leaf timeout {
            type string;
          }
          container trunk {
            leaf number {
              type string;
            }
            leaf admin-key {
              // NCS drop must statement
              type string;
            }
            leaf mode {
              // NCS drop must statement
              type string;
            }
            leaf unidirectional-detection {
              // NCS drop must statement
              type empty;
            }
          }
          container udld-timeout {
            leaf timeout-type {
              type string;
            }
            leaf milli {
              // NCS drop when statement
              type string;
            }
            leaf secs {
              // NCS drop when statement
              type string;
            }
          }
        }
        leaf load-interval {
          type string;
        }
        leaf mtu {
          type string;
          // NCS drop default statement
        }
        leaf name {
          type string;
        }
        leaf speed {
          type string;
          // NCS drop default statement
        }
      }
      list ve {
        // NCS patched for predictable order
        ordered-by user;
        key "id";
        leaf id {
          type string;
        }
        container access-list {
          leaf id {
            type string;
          }
          leaf in {
            // NCS drop must statement
            type empty;
          }
        }
        leaf enabled-disabled {
          type string;
          // NCS drop default statement
        }
        container icmp-rate-limit {
          leaf rate {
            type string;
          }
          leaf lockup {
            // NCS drop must statement
            type string;
          }
          leaf lockup-perio {
            // NCS drop must statement
            type string;
          }
        }
        container ip {
          list address {
            // NCS patched for predictable order
            ordered-by user;
            key "ip";
            leaf ip {
              type string;
            }
            leaf mask {
              type string;
            }
          }
          leaf allow-promiscuous-vip {
            type empty;
          }
          leaf cache-spoofing-port {
            type empty;
          }
          leaf helper-address {
            type string;
          }
          container nat {
            leaf inside {
              type empty;
            }
            leaf outside {
              type empty;
            }
          }
          container ospf;
          container router {
            container isis {
              presence "true";
              leaf cmds {
                type string;
              }
            }
          }
          container tcp {
            leaf syn-cookie {
              type empty;
            }
          }
        }
        container ipv6 {
          container access-list {
            leaf id {
              type string;
            }
            leaf in {
              // NCS drop must statement
              type empty;
            }
          }
          list address {
            // NCS patched for predictable order
            ordered-by user;
            key "ip";
            leaf ip {
              type string;
            }
            leaf link-local {
              type empty;
            }
            leaf anycast {
              type empty;
            }
          }
          container nat {
            leaf inside {
              type empty;
            }
            leaf outside {
              type empty;
            }
          }
          container ndisc {
            container router-advertisement;
          }
          container ospf;
          container router {
            container isis {
              presence "true";
              leaf cmds {
                type string;
              }
            }
          }
        }
        container isis;
        leaf l3-vlan-fwd-disable {
          type empty;
        }
        leaf name {
          type string;
        }
        container ospf;
      }
    }
    container ip {
      list address {
        // NCS patched for predictable order
        ordered-by user;
        key "ip";
        leaf ip {
          type string;
        }
        leaf mask {
          type string;
        }
      }
      container anomaly-drop {
        leaf bad-content {
          type string;
        }
        leaf drop-all {
          type empty;
        }
        leaf frag {
          type empty;
        }
        leaf ip-option {
          type empty;
        }
        leaf land-attack {
          type empty;
        }
        leaf out-of-sequence {
          type string;
        }
        leaf ping-of-death {
          type empty;
        }
        leaf tcp-no-flag {
          type empty;
        }
        leaf tcp-syn-fin {
          type empty;
        }
        leaf tcp-syn-frag {
          type empty;
        }
        leaf zero-window {
          type string;
        }
      }
      container as-path {
        list access-list {
          // NCS patched for predictable order
          ordered-by user;
          key "name action path";
          leaf name {
            type string;
          }
          leaf action {
            type string;
          }
          leaf path {
            type string;
          }
        }
      }
      container community-list {
        list standard-number {
          // NCS patched for predictable order
          ordered-by user;
          key "nr";
          leaf nr {
            type string;
          }
          list rules {
            // NCS patched for predictable order
            ordered-by user;
            key "action expr";
            leaf action {
              type string;
            }
            leaf expr {
              type string;
            }
          }
        }
        list expanded-number {
          // NCS patched for predictable order
          ordered-by user;
          key "nr";
          leaf nr {
            type string;
          }
          list rules {
            // NCS patched for predictable order
            ordered-by user;
            key "action expr";
            leaf action {
              type string;
            }
            leaf expr {
              type string;
            }
          }
        }
        list word {
          // NCS patched for predictable order
          ordered-by user;
          key "name";
          leaf name {
            type string;
          }
          list rules {
            // NCS patched for predictable order
            ordered-by user;
            key "action expr";
            leaf action {
              type string;
            }
            leaf expr {
              type string;
            }
          }
        }
        list expanded {
          // NCS patched for predictable order
          ordered-by user;
          key "name";
          leaf name {
            type string;
          }
          list rules {
            // NCS patched for predictable order
            ordered-by user;
            key "action expr";
            leaf action {
              type string;
            }
            leaf expr {
              type string;
            }
          }
        }
        list standard {
          // NCS patched for predictable order
          ordered-by user;
          key "name";
          leaf name {
            type string;
          }
          list rules {
            // NCS patched for predictable order
            ordered-by user;
            key "action expr";
            leaf action {
              type string;
            }
            leaf expr {
              type string;
            }
          }
        }
      }
      leaf default-gateway {
        type string;
      }
      container dns {
        leaf primary {
          type string;
        }
        leaf secondary {
          type string;
        }
        leaf suffix {
          type string;
        }
      }
      container extcommunity-list {
        list standard-number {
          // NCS patched for predictable order
          ordered-by user;
          key "nr";
          leaf nr {
            type string;
          }
          list rules {
            // NCS patched for predictable order
            ordered-by user;
            key "action expr";
            leaf action {
              type string;
            }
            leaf expr {
              type string;
            }
          }
        }
        list expanded-number {
          // NCS patched for predictable order
          ordered-by user;
          key "nr";
          leaf nr {
            type string;
          }
          list rules {
            // NCS patched for predictable order
            ordered-by user;
            key "action expr";
            leaf action {
              type string;
            }
            leaf expr {
              type string;
            }
          }
        }
        list expanded {
          // NCS patched for predictable order
          ordered-by user;
          key "name";
          leaf name {
            type string;
          }
          list rules {
            // NCS patched for predictable order
            ordered-by user;
            key "action expr";
            leaf action {
              type string;
            }
            leaf expr {
              type string;
            }
          }
        }
        list standard {
          // NCS patched for predictable order
          ordered-by user;
          key "name";
          leaf name {
            type string;
          }
          list rules {
            // NCS patched for predictable order
            ordered-by user;
            key "action expr";
            leaf action {
              type string;
            }
            leaf expr {
              type string;
            }
          }
        }
      }
      container frag {
        leaf buff {
          type string;
        }
        leaf max-reassembly-sessions {
          type string;
        }
        leaf timeout {
          type string;
        }
      }
      container icmp {
        container disable {
          leaf redirect {
            type empty;
          }
          leaf unreachable {
            type empty;
          }
        }
      }

      grouping mgmt-source-interface-grouping {
        container source-interface {
          leaf loopback {
            type string;
          }
        }
      }
      container mgmt-traffic {
        container snmp {
          uses mgmt-source-interface-grouping;
        }
        container ntp {
          uses mgmt-source-interface-grouping;
        }
        container syslog {
          uses mgmt-source-interface-grouping;
        }
        container ssh {
          uses mgmt-source-interface-grouping;
        }
        container telnet {
          uses mgmt-source-interface-grouping;
        }
        container ftp {
          uses mgmt-source-interface-grouping;
        }
        container tftp {
          uses mgmt-source-interface-grouping;
        }
        container rcp {
          uses mgmt-source-interface-grouping;
        }
        container web {
          uses mgmt-source-interface-grouping;
        }
        container all {
          uses mgmt-source-interface-grouping;
        }
      }
      container nat {
        container alg {
          leaf pptp {
            type string;
            // NCS drop default statement
          }
        }
        leaf allow-static-host {
          type empty;
        }
        container inside {
          container source;
        }
        list pool {
          // NCS patched for predictable order
          ordered-by user;
          key "name";
          leaf name {
            type string;
          }
          leaf ipstart {
            // NCS drop mandatory statement
            type string;
          }
          leaf ipend {
            // NCS drop mandatory statement
            type string;
          }
          leaf netmask {
            // NCS drop mandatory statement
            type string;
          }
          leaf gateway {
            type string;
          }
          leaf ha-group-id {
            type string;
          }
          leaf ha-use-all-ports {
            type empty;
            // NCS drop when statement
          }
          leaf vrid {
            // NCS drop when statement
            type string;
          }
          leaf ip-rr {
            type empty;
          }
        }
        container pool-group;
        container range-list;
        leaf reset-idle-tcp-conn {
          type empty;
        }
        container template {
          list logging {
            // NCS patched for predictable order
            ordered-by user;
            key "name";
            leaf name {
              type string;
            }
          }
        }
        container translation;
      }
      container prefix-list;
      list route {
        // NCS patched for predictable order
        ordered-by user;
        key "ip mask";
        leaf ip {
          type string;
        }
        leaf mask {
          type string;
        }
        leaf forwarding-router {
          type string;
        }
        leaf distance {
          // NCS drop must statement
          type string;
        }
      }
      container tcp {
        container syn-cookie {
          leaf threshold {
            type string;
          }
        }
      }
    }
    container floating-ip {
      list ipv4 {
        // NCS patched for predictable order
        ordered-by user;
        key "ip";
        leaf ip {
          type string;
        }
        leaf ha-group {
          type string;
        }
      }
      list ipv6 {
        // NCS patched for predictable order
        ordered-by user;
        key "ip";
        leaf ip {
          type string;
        }
        leaf anycast {
          type empty;
        }
        leaf ha-group {
          type string;
        }
      }
    }
    container health {
      list monitor {
        // NCS patched for predictable order
        ordered-by user;
        key "name";
        leaf name {
          type string;
        }
        leaf interval {
          type string;
        }
        leaf retry {
          type string;
          // NCS drop default statement
        }
        leaf timeout {
          type string;
          // NCS drop default statement
        }
        leaf up-retry {
          type string;
          // NCS drop default statement
        }
        leaf strictly-retry-on-server-error-response {
          type empty;
        }
        leaf disable-after-down {
          type empty;
        }
        leaf override-port {
          type string;
        }
        leaf override-ipv4 {
          type string;
        }
        leaf override-ipv6 {
          type string;
        }
        container method {
          choice method-choice {
            container icmp {
              presence "true";
              leaf transparent {
                type string;
              }
            }
            container http {
              presence "true";
              leaf port {
                type string;
                // NCS drop default statement
              }
              container username {
                leaf name {
                  type string;
                }
                leaf password {
                  // NCS drop must statement
                  type empty;
                }
                leaf cleartext {
                  type string;
                }
                leaf encrypted {
                  // NCS drop when statement
                  type string;
                }
              }
              container url {
                leaf method {
                  type string;
                }
                leaf path {
                  // NCS drop must statement
                  type string;
                }
              }
              container expect {
                choice expect-choice {
                  leaf response-code {
                    type string;
                  }
                  leaf text {
                    type string;
                  }
                }
              }
              leaf maintenance-code {
                type string;
              }
              leaf host {
                type string;
              }
            }
            container https {
              presence "true";
              leaf port {
                type string;
                // NCS drop default statement
              }
              leaf disable-sslv2hello {
                type empty;
              }
              container username {
                leaf name {
                  type string;
                }
                leaf password {
                  // NCS drop must statement
                  type empty;
                }
                leaf cleartext {
                  type string;
                }
                leaf encrypted {
                  // NCS drop when statement
                  type string;
                }
              }
              container url {
                leaf method {
                  type string;
                }
                leaf path {
                  // NCS drop must statement
                  type string;
                }
              }
              container expect {
                choice expect-choice {
                  leaf response-code {
                    type string;
                  }
                  leaf text {
                    type string;
                  }
                }
              }
              leaf maintenance-code {
                type string;
              }
              leaf host {
                type string;
              }
            }
            container tcp {
              leaf port {
                type string;
              }
              leaf halfopen {
                type empty;
              }
            }
            container udp {
              leaf port {
                type string;
              }
            }
            container ftp {
              leaf port {
                type string;
                // NCS drop default statement
              }
              container credentials {
                presence "FTP credentials";
                leaf username {
                  type string;
                }
                container password {
                  choice ftp-pass-choice {
                    leaf cleartext {
                      type string;
                    }
                    leaf encrypted {
                      type string;
                    }
                  }
                }
              }
            }
            container snmp {
              leaf community {
                type string;
              }
              leaf oid {
                type string;
              }
              leaf operation {
                type string;
              }
              leaf port {
                type string;
                // NCS drop default statement
              }
            }
            container smtp {
              leaf domain {
                type string;
              }
              leaf port {
                type string;
                // NCS drop default statement
              }
            }
            container dns {
              choice dns-health-choice {
                leaf domain {
                  type string;
                }
                leaf ipaddress {
                  type string;
                }
              }
              container expect {
                leaf response-code {
                  type string;
                }
              }
              leaf port {
                type string;
                // NCS drop default statement
              }
              leaf recurse {
                type string;
              }
              leaf type {
                // NCS drop when statement
                type string;
              }
            }
            container pop3 {
              leaf port {
                type string;
                // NCS drop default statement
              }
              container credentials {
                presence "POP3 credentials";
                leaf username {
                  type string;
                }
                container password {
                  choice ftp-pass-choice {
                    leaf cleartext {
                      type string;
                    }
                    leaf encrypted {
                      type string;
                    }
                  }
                }
              }
            }
            container imap {
              leaf port {
                type string;
                // NCS drop default statement
              }
              container credentials {
                presence "IMAP credentials";
                leaf username {
                  type string;
                }
                container password {
                  choice ftp-pass-choice {
                    leaf cleartext {
                      type string;
                    }
                    leaf encrypted {
                      type string;
                    }
                  }
                }
              }
              leaf-list auth {
                // NCS patched for predictable order
                ordered-by user;
                // NCS drop when statement
                type string;
              }
            }
            container sip {
              leaf port {
                type string;
                // NCS drop default statement
              }
              leaf register {
                type empty;
              }
              leaf tcp {
                type empty;
              }
            }
            container radius {
              leaf port {
                type string;
                // NCS drop default statement
              }
              leaf secret {
                type string;
              }
              container credentials {
                presence "RADIUS credentials";
                leaf username {
                  type string;
                }
                container password {
                  choice ftp-pass-choice {
                    leaf cleartext {
                      type string;
                    }
                    leaf encrypted {
                      type string;
                    }
                  }
                }
              }
            }
            container ldap {
              leaf port {
                type string;
              }
              leaf overssl {
                type empty;
              }
              container binddn {
                leaf name {
                  type string;
                }
                container password {
                  choice ftp-pass-choice {
                    leaf cleartext {
                      type string;
                    }
                    leaf encrypted {
                      type string;
                    }
                  }
                }
              }
            }
            container rtsp {
              leaf port {
                type string;
              }
              leaf rtspurl {
                type string;
              }
            }
            container database {
              leaf dbtype {
                type string;
              }
              leaf db-name {
                // NCS drop when statement
                // NCS drop mandatory statement
                type string;
              }
              leaf username {
                // NCS drop when statement
                // NCS drop mandatory statement
                type string;
              }
              container password {
                // NCS drop when statement
                choice db-pass-choice {
                  leaf cleartext {
                    type string;
                  }
                  leaf encrypted {
                    type string;
                  }
                }
              }
              leaf send {
                type string;
              }
              leaf receive {
                type string;
              }
              leaf row {
                type string;
              }
              leaf column {
                type string;
              }
            }
            container external;
            container ntp;
            container compound;
          }
        }
      }
    }
    leaf stats-data-disable {
      type empty;
    }
    container syn-cookie {
      leaf on-threshold {
        type string;
      }
      leaf off-threshold {
        type string;
      }
    }
    container slb {
      container graceful-shutdown {
        leaf timeout {
          type string;
        }
        leaf when {
          // NCS drop must statement
          type string;
        }
      }
      container buff-thresh {
        leaf hw-buff {
          type string;
        }
        leaf relieve-thresh {
          type string;
        }
        leaf sys-buff-low {
          type string;
        }
        leaf sys-buff-high {
          type string;
        }
      }
      container template {
        list server {
          // NCS patched for predictable order
          ordered-by user;
          key "name";
          leaf name {
            type string;
          }
          leaf health-check {
            type string;
            // NCS drop default statement
          }
          container conn-limit {
            leaf limit {
              type string;
            }
            leaf resume {
              // NCS drop must statement
              type string;
            }
            leaf no-logging {
              type empty;
            }
          }
          container conn-rate-limit {
            leaf limit {
              type string;
            }
            leaf per {
              // NCS drop must statement
              type string;
            }
            leaf no-logging {
              type empty;
            }
          }
          leaf dns-query-interval {
            type string;
          }
          leaf dynamic-server-prefix {
            type string;
            // NCS drop default statement
          }
          leaf max-dynamic-server {
            type string;
            // NCS drop default statement
          }
          leaf min-ttl-ratio {
            type string;
            // NCS drop default statement
          }
          container slow-start {
            leaf from {
              type string;
            }
            choice slow-start-choice {
              leaf add {
                type string;
              }
              leaf times {
                type string;
              }
            }
            leaf every {
              type string;
            }
            leaf till {
              type string;
            }
          }
        }
        list port {
          // NCS patched for predictable order
          ordered-by user;
          key "name";
          leaf name {
            type string;
          }
          leaf health-check {
            type string;
            // NCS drop default statement
          }
          container conn-limit {
            leaf limit {
              type string;
            }
            leaf resume {
              // NCS drop must statement
              type string;
            }
            leaf no-logging {
              type empty;
            }
          }
          container conn-rate-limit {
            leaf limit {
              type string;
            }
            leaf per {
              // NCS drop must statement
              type string;
            }
            leaf no-logging {
              type empty;
            }
          }
          leaf dest-nat {
            type empty;
          }
          leaf down-grace-period {
            type string;
          }
          leaf dscp {
            type string;
          }
          container dynamic-member-priority {
            leaf priority {
              type string;
            }
            leaf decrement {
              // NCS drop must statement
              type string;
            }
          }
          container inband-health-check {
            presence "true";
            leaf retry {
              type string;
            }
            leaf reassign {
              type string;
            }
          }
          container slow-start {
            leaf from {
              type string;
            }
            choice slow-start-choice {
              leaf add {
                type string;
              }
              leaf times {
                type string;
              }
            }
            leaf every {
              type string;
            }
            leaf till {
              type string;
            }
          }
          leaf source-nat {
            type string;
          }
          leaf weight {
            type string;
          }
        }
        container cache;
        container client-ssl;
        container connection-reuse;
        container diameter;
        container dns;
        container http;
        container persist {
          list source-ip {
            // NCS patched for predictable order
            ordered-by user;
            key "name";
            leaf name {
              type string;
            }
            leaf dont-honor-conn-rules {
              type empty;
            }
            leaf enforce-higher-priority {
              type empty;
            }
            leaf incl-sport {
              type empty;
            }
            container match-type {
              choice match-choice {
                container server {
                  presence "true";
                  leaf scan-all-members {
                    type empty;
                  }
                }
                leaf service-group {
                  type empty;
                }
              }
            }
            leaf netmask {
              type string;
            }
            leaf netmask6 {
              type string;
            }
            leaf timeout {
              type string;
            }
          }
        }
        container policy;
        container server-ssl;
        container sip;
        container smtp;
        container streaming-media;
        list tcp {
          // NCS patched for predictable order
          ordered-by user;
          key "name";
          leaf name {
            type string;
          }
          leaf idle-timeout {
            type string;
          }
          container force-delete-timeout {
            leaf timeout {
              type string;
            }
            leaf alive-if-active {
              // NCS drop must statement
              type empty;
            }
          }
          leaf half-close-idle-timeout {
            type string;
          }
          leaf initial-window-size {
            type string;
          }
          leaf lan-fast-ack {
            type empty;
          }
          leaf reset-fwd {
            type empty;
          }
          leaf reset-rev {
            type empty;
          }
        }
        container tcp-proxy;
        container udp;
        container virtual-port;
        list virtual-server {
          // NCS patched for predictable order
          ordered-by user;
          key "name";
          leaf name {
            type string;
          }
          container conn-limit {
            leaf limit {
              type string;
            }
            leaf reset {
              // NCS drop must statement
              type empty;
            }
            leaf no-logging {
              type empty;
            }
          }
          container conn-rate-limit {
            leaf limit {
              type string;
            }
            leaf per {
              // NCS drop must statement
              type string;
            }
            leaf reset {
              // NCS drop must statement
              type empty;
            }
            leaf no-logging {
              type empty;
            }
          }
          container icmp-rate-limit {
            leaf rate {
              type string;
            }
            leaf lockup {
              // NCS drop must statement
              type string;
            }
            leaf lockup-perio {
              // NCS drop must statement
              type string;
            }
          }
          leaf subnet-gratuitous-arp {
            type empty;
          }
        }
      }
      list server {
        // NCS patched for predictable order
        ordered-by user;
        key "name";
        unique "address";
        leaf name {
          type string;
        }
        leaf address {
          type string;
        }
        container health-check {
          leaf host {
            type string;
          }
        }
        container conn-limit {
          leaf limit {
            type string;
          }
          leaf resume {
            // NCS drop must statement
            type string;
          }
          leaf no-logging {
            type empty;
          }
        }
        leaf conn-resume {
          type string;
        }
        leaf extended-stats {
          type empty;
        }
        leaf external-ip {
          type string;
        }
        container ha-priority-cost {
          leaf cost {
            type string;
          }
          leaf ha-group {
            // NCS drop must statement
            type string;
          }
        }
        leaf ipv6 {
          type string;
        }
        leaf slow-start {
          type empty;
        }
        leaf spoofing-cache {
          type empty;
        }
        leaf stats-data-disable {
          type empty;
        }
        leaf weight {
          type string;
        }
        list port {
          // NCS patched for predictable order
          ordered-by user;
          key "number tcpudp";
          leaf number {
            type string;
          }
          leaf tcpudp {
            type string;
          }
          container conn-limit {
            leaf limit {
              type string;
            }
            leaf resume {
              // NCS drop must statement
              type string;
            }
            leaf no-logging {
              type empty;
            }
          }
          leaf conn-resume {
            type string;
          }
          leaf extended-stats {
            type empty;
          }
          container ha-priority-cost {
            leaf cost {
              type string;
            }
            leaf ha-group {
              // NCS drop must statement
              type string;
            }
          }
          container health-check {
            leaf host {
              type string;
            }
          }
          leaf no-ssl {
            type empty;
          }
          leaf stats-data-disable {
            type empty;
          }
        }
        container template {
          leaf server {
            type string;
          }
        }
      }
      list service-group {
        // NCS patched for predictable order
        ordered-by user;
        key "name";
        leaf name {
          type string;
        }
        leaf tcpudp {
          // NCS drop mandatory statement
          type string;
        }
        leaf backup-server-event-log {
          type empty;
        }
        leaf extended-stats {
          type empty;
        }
        container health-check {
          leaf host {
            type string;
          }
        }
        list member {
          // NCS patched for predictable order
          ordered-by user;
          key "host port";
          leaf host {
            type string;
          }
          leaf port {
            type string;
          }
        }
        container method {
          choice method-choice {
            leaf fastest-response {
              type empty;
            }
            container least-connection {
              presence "true";
              leaf pseudo-round-robin {
                type empty;
              }
            }
            leaf least-request {
              type empty;
            }
            leaf round-robin {
              type empty;
            }
            leaf round-robin-strict {
              type empty;
            }
            container service-least-connection {
              presence "true";
              leaf pseudo-round-robin {
                type empty;
              }
            }
            container service-weighted-least-connection {
              presence "true";
              leaf pseudo-round-robin {
                type empty;
              }
            }
            leaf stateless-dst-ip-hash {
              type empty;
            }
            leaf stateless-per-pkt-round-robin {
              type empty;
            }
            leaf stateless-src-dst-ip-hash {
              type empty;
            }
            leaf stateless-src-ip-hash {
              type empty;
            }
            leaf stateless-src-ip-only-hash {
              type empty;
            }
            container weighted-least-connection {
              presence "true";
              leaf pseudo-round-robin {
                type empty;
              }
            }
            leaf weighted-rr {
              type empty;
            }
          }
        }
        container min-active-member {
          leaf min {
            type string;
          }
          leaf method {
            // NCS drop must statement
            type string;
          }
        }
        container priority {
          leaf prio {
            type string;
          }
          leaf action {
            type string;
          }
        }
        container priority-affinity {
          presence "true";
        }
        leaf reset-on-server-selection-fail {
          type empty;
        }
        leaf stats-data-disable {
          type empty;
        }
      }
      list virtual-server {
        // NCS patched for predictable order
        ordered-by user;
        key "name address";
        unique "address";
        leaf name {
          type string;
        }
        leaf address {
          type string;
        }
        leaf netmask {
          type string;
        }
        leaf acl {
          type string;
        }
        leaf arp-disable {
          type empty;
        }
        leaf disable {
          type empty;
        }
        leaf extended-stats {
          type empty;
        }
        leaf ha-dynamic {
          type string;
        }
        leaf ha-group {
          type string;
        }
        leaf redistribution-flagged {
          type empty;
        }
        leaf stats-data-disable {
          type empty;
        }
        leaf vrid {
          type string;
        }
        list port {
          // NCS patched for predictable order
          ordered-by user;
          key "id";
          // NCS drop must statement
          leaf id {
            type string;
          }
          leaf type {
            // NCS drop mandatory statement
            type string;
          }
          container access-list {
            choice access-list-id {
              leaf acl-id {
                type string;
              }
              leaf name {
                type string;
              }
            }
            leaf source-nat-pool {
              type string;
            }
            leaf sequence-number {
              type string;
            }
          }
          leaf aflex {
            type string;
          }
          container conn-limit {
            leaf limit {
              type string;
            }
            leaf reset {
              // NCS drop must statement
              type empty;
            }
            leaf no-logging {
              type empty;
            }
          }
          leaf def-selection-if-pref-failed {
            type empty;
          }
          leaf disable {
            type empty;
          }
          leaf extended-stats {
            type empty;
          }
          leaf ha-conn-mirror {
            type empty;
            // NCS drop must statement
          }
          leaf name {
            type string;
          }
          container no-dest-nat {
            presence "true";
            leaf port-translation {
              type empty;
            }
          }
          leaf pbslb {
            type empty;
          }
          leaf reset-on-server-selection-fail {
            type empty;
          }
          leaf service-group {
            type string;
          }
          leaf snat-on-vip {
            type empty;
          }
          container source-nat {
            choice source-nat-choice {
              container auto {
                presence "true";
                leaf precedence {
                  type empty;
                }
              }
              leaf pool {
                type string;
              }
            }
          }
          leaf stats-data-disable {
            type empty;
          }
          leaf syn-cookie {
            type empty;
          }
          container use-default-if-no-server {
            presence "true";
            leaf sack {
              type empty;
            }
          }
          leaf use-rcv-hop-for-resp {
            type empty;
          }
          container template {
            leaf diameter {
              type string;
            }
            container persist {
              leaf destination-ip {
                type string;
              }
              leaf source-ip {
                type string;
              }
              leaf ssl-sid {
                type string;
              }
            }
            leaf policy {
              type string;
            }
            leaf tcp {
              type string;
            }
            leaf virtual-port {
              type string;
            }
          }
        }
        container template {
          leaf logging {
            type string;
          }
          leaf policy {
            type string;
          }
          leaf virtual-server {
            type string;
          }
        }
      }
    }
    container logging {
      container auditlog;
      container buffered {
        leaf size {
          type string;
        }
        leaf severity {
          type string;
        }
      }
      leaf console {
        type string;
      }
      container email {
        container buffer {
          choice buffer-choice {
            leaf number {
              type string;
              // NCS drop default statement
            }
            leaf time {
              type string;
              // NCS drop default statement
            }
          }
        }
        leaf severity {
          type string;
        }
      }
      leaf-list email-address {
        // NCS patched for predictable order
        ordered-by user;
        type string;
      }
      leaf export {
        type empty;
      }
      leaf facility {
        type string;
      }
      leaf syslog {
        type string;
      }
      leaf trap {
        type string;
      }
      container host {
        leaf-list hosts {
          // NCS patched for predictable order
          ordered-by user;
          type string;
        }
        leaf port {
          type string;
        }
      }
      leaf monitor {
        type string;
      }
    }
    container snmp-server {
      container enable {
        leaf enabled {
          type empty;
        }
        container traps {
          leaf enabled {
            type empty;
          }
          container routing {
            container ospf {
              choice routing-choice {
                leaf-list ospf-traps {
                  // NCS patched for predictable order
                  ordered-by user;
                  type string;
                }
                leaf all {
                  type empty;
                }
              }
            }
          }
          container snmp {
            leaf enabled {
              type empty;
            }
            leaf linkdown {
              type empty;
            }
            leaf linkup {
              type empty;
            }
          }
          container ha {
            leaf enabled {
              type empty;
            }
            leaf active {
              type empty;
            }
            leaf active-active {
              type empty;
            }
            leaf standby {
              type empty;
            }
            leaf vrrp {
              type empty;
            }
          }
          container network {
            leaf enabled {
              type empty;
            }
            leaf trunk-port-threshold {
              type empty;
            }
          }
          container slb {
            leaf enabled {
              type empty;
            }
            leaf application-buffer-limit {
              type empty;
            }
            leaf server-conn-limit {
              type empty;
            }
            leaf server-conn-resume {
              type empty;
            }
            leaf server-down {
              type empty;
            }
            leaf server-up {
              type empty;
            }
            leaf service-conn-limit {
              type empty;
            }
            leaf service-conn-resume {
              type empty;
            }
            leaf service-down {
              type empty;
            }
            leaf service-up {
              type empty;
            }
            leaf vip-connlimit {
              type empty;
            }
            leaf vip-connratelimit {
              type empty;
            }
            leaf vip-port-connlimit {
              type empty;
            }
            leaf vip-port-connratelimit {
              type empty;
            }
            leaf vip-port-down {
              type empty;
            }
            leaf vip-port-up {
              type empty;
            }
          }
          container system {
            leaf enabled {
              type empty;
            }
            leaf control-cpu-high {
              type empty;
            }
            leaf data-cpu-high {
              type empty;
            }
            leaf fan {
              type empty;
            }
            leaf high-disk-use {
              type empty;
            }
            leaf high-memory-use {
              type empty;
            }
            leaf high-temp {
              type empty;
            }
            leaf packet-drop {
              type empty;
            }
            leaf power {
              type empty;
            }
            leaf pri-disk {
              type empty;
            }
            leaf restart {
              type empty;
            }
            leaf sec-disk {
              type empty;
            }
            leaf shutdown {
              type empty;
            }
            leaf start {
              type empty;
            }
          }
        }
      }
      leaf location {
        type string;
      }
      list user {
        // NCS patched for predictable order
        ordered-by user;
        key "name group type";
        leaf name {
          type string;
        }
        leaf group {
          type string;
        }
        leaf type {
          type string;
        }
        container auth {
          // NCS drop when statement
          leaf mac {
            type string;
          }
          leaf cleartext {
            type string;
          }
          leaf pw-encrypted {
            // NCS drop when statement
            type string;
          }
          leaf encrypted {
            // NCS drop must statement
            type empty;
          }
        }
      }
      list view {
        // NCS patched for predictable order
        ordered-by user;
        key "name";
        leaf name {
          type string;
        }
      }
      container group;
      list community {
        // NCS patched for predictable order
        ordered-by user;
        key "read remote";
        leaf read {
          type string;
        }
        leaf remote {
          type string;
        }
        leaf oid {
          type string;
        }
        leaf mask {
          type string;
        }
      }
      leaf contact {
        type string;
      }
      list host {
        // NCS patched for predictable order
        ordered-by user;
        key "ip version";
        leaf ip {
          type string;
        }
        leaf version {
          type string;
        }
        leaf community-string {
          // NCS drop mandatory statement
          type string;
        }
        leaf udp-port {
          // NCS drop mandatory statement
          type string;
        }
      }
    }
    container terminal {
      leaf auto-size {
        type empty;
      }
      leaf editing {
        type empty;
      }
      container history {
        leaf size {
          type string;
          // NCS drop default statement
        }
      }
      leaf idle-timeout {
        type string;
      }
      leaf length {
        type string;
      }
      leaf no-ha-prompt {
        type empty;
      }
      leaf width {
        type string;
      }
    }
    container authentication {
      leaf-list type {
        // NCS patched for predictable order
        ordered-by user;
        type string;
      }
      container console {
        leaf-list type {
          // NCS patched for predictable order
          ordered-by user;
          type string;
        }
      }
      leaf disable-local {
        type empty;
      }
    }
    leaf enable-core {
      type empty;
    }
  }
}
