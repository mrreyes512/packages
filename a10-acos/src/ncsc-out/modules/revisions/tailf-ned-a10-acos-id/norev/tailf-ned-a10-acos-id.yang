module tailf-ned-a10-acos-id {
  // Generated by yanger -t ncs
  tailf:ncs-device-type "cli-ned";

  namespace "http://tail-f.com/ned/a10-acos-id";
  prefix a10-acos-id;

  import tailf-ncs-ned {
    prefix ned;
  }
  import tailf-ncs {
    prefix ncs;
  }
  import tailf-common {
    prefix tailf;
  }

  identity a10-acos {
    base ned:cli-ned-id;
  }
}
